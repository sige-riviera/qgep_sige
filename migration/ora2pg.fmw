FME workspace ora2pg.fmw

Parameters:
- SourceDataset_ORACLE_NONSPATIAL = SYSTEM@orcl   # Connection
- SourceDataset_ORACLE_NONSPATIAL_9 = SYSTEM@orcl   # Connection
- SourceDataset_ORACLE_NONSPATIAL_13 = SYSTEM@orcl   # Connection
- DestDataset_POSTGRES = topobase_dump   # Database
- DestDataset_POSTGRES_7 = topobase_dump   # Database
- SourceDataset_ORACLE_NONSPATIAL_11 = SYSTEM@orcl   # Connection
- DestDataset_POSTGRES_9 = topobase_dump   # Database
- SourceDataset_ORACLE_NONSPATIAL_8 = SYSTEM@orcl   # Connection
- SourceDataset_ORACLE_NONSPATIAL_10 = SYSTEM@orcl   # Connection
- DestDataset_POSTGRES_10 = sige@172.24.171.203:5432/topobase_dump   # Connection
- SourceDataset_ORACLE_NONSPATIAL_12 = SYSTEM@orcl   # Connection
- DestDataset_POSTGRES_6 = sige@172.24.171.203:5432/topobase_dump   # Connection

Readers:
- ORACLE_NONSPATIAL_1: ORACLE_NONSPATIAL from $(SourceDataset_ORACLE_NONSPATIAL)
- ORACLE_NONSPATIAL_2: ORACLE_NONSPATIAL from $(SourceDataset_ORACLE_NONSPATIAL_9)
- ORACLE_NONSPATIAL_3: ORACLE_NONSPATIAL from $(SourceDataset_ORACLE_NONSPATIAL_13)
- ORACLE_NONSPATIAL_4: ORACLE_NONSPATIAL from $(SourceDataset_ORACLE_NONSPATIAL_11)
- ORACLE_NONSPATIAL_5: ORACLE_NONSPATIAL from $(SourceDataset_ORACLE_NONSPATIAL_8)
- ORACLE_NONSPATIAL_6: ORACLE_NONSPATIAL from $(SourceDataset_ORACLE_NONSPATIAL_10)
- ORACLE_NONSPATIAL_7: ORACLE_NONSPATIAL from $(SourceDataset_ORACLE_NONSPATIAL_12)

Writers:
- POSTGRES_1: POSTGRES to $(DestDataset_POSTGRES)
- POSTGRES_2: POSTGRES to $(DestDataset_POSTGRES_7)
- POSTGRES_3: POSTGRES to $(DestDataset_POSTGRES_9)
- POSTGRES_4: POSTGRES to $(DestDataset_POSTGRES_10)
- POSTGRES_5: POSTGRES to $(DestDataset_POSTGRES_6)

Note: chambre
SIGE_ASSAINISSEMENT.AW_SCHACHT (reader ORACLE_NONSPATIAL_1)
    attributes: FID number(10,0), GID number(10,0), DELETED number(1,0), AREA_NOMINAL number(20,8), POINT_NUMBER varchar2(50), NAME varchar2(60), SONDERBAUWERK varchar2(20), SBW number(20,0), NAME2 varchar2(20), BEMERKUNG varchar2(255), F1 varchar2(20), F2 varchar2(20), F3 varchar2(20), TIEFE number(20,5), BAUJAHR number(20,0), DN number(20,5), BREITE number(20,5), UNTEN_DN number(20,5), UNTEN_BREITE number(20,5), WANDDICKE number(20,5), SCHACHTHALS varchar2(5), ANSCHLUESSE number(20,5), UEBERGANGSPLATTE varchar2(5), ABDECKPLATTE varchar2(5), BAUGRUBENBREITE number(20,5), BOESCHUNGSWINKEL number(20,5), FLAECHE number(20,5), UEBERSTAUHAEUFIGKEIT number(20,5), LETZTER_UEBERSTAU date, BEZEICHNUNG1 varchar2(20),
      BEZEICHNUNG2 varchar2(20), SKALIERFAKTOR number(20,5), ORTSBEZEICHNUNG varchar2(50), UNTEN_HOEHE number(20,5), ANZAHL_EINLAEUFE number(2,0), ANZAHL_AUSLAEUFE number(2,0), TB_POINT_NUMBER number(15,0), KOMPLEX_LABEL varchar2(2000), ID_STATUS number(10,0), ID_STRASSE number(10,0), ID_LAGE number(10,0), ID_SCHACHTART number(10,0), ID_ZUGAENGLICHKEIT number(10,0), ID_FUNKTION number(10,0), ID_MATERIAL number(10,0), ID_FINANZIERUNGSKENNZIFFER number(10,0), ID_HOEHENGENAUIGKEIT number(10,0), ID_LAGEGENAUIGKEIT number(10,0), ID_KONUS_BAUSTOFF number(10,0), ID_OBEN_BAUSTOFF number(10,0), ID_EINSTIEGHILFE number(10,0), ID_UNTEN_BAUSTOFF number(10,0), ID_GERINNE_BAUSTOFF number(10,0), ID_GRUENDUNG number(10,0), ID_SCHACHT_FORM number(10,0), ID_UNTEN_FORM number(10,0), ID_BEGR_BESCHICHTUNG number(10,0), ID_STEIGEISENGAENGE number(10,0), ID_VERKEHRSFLAECHE number(10,0), ID_GERINNE_FORM number(10,0),
      ID_NUTZUNGS_ART number(10,0), ID_BESCHICHTUNG_INNEN number(10,0), ID_BESCHICHTUNG_AUSSEN number(10,0), ID_EIGENTUMSVERHAELTNIS number(10,0), ID_BAUGRUBENFORM number(10,0), FID_KS number(10,0), FID_LAGEBEZEICHNUNG number(10,0), FID_EINRICHTUNGS_TYP number(10,0), CHAMBRE_ANCIENID varchar2(20), FID_COLLECTEUR number(10,0), ID_COMMUNE number(10,0), CHAMBRE_PLAN varchar2(20), ID_BRISECHARGE number(10,0), ID_COUPEVENT number(10,0), ID_LIMITEURDEBIT number(10,0), ID_PROFIL number(10,0), CHAMBRE_CONTROLE date, CHAMBRE_NUMEROECA varchar2(50), CHAMBRE_PARCELLE varchar2(20), CHAMBRE_CLASSE varchar2(50), CHAMBRE_TYPE varchar2(50), ID_AERATION number(10,0), DATE_REHABIL date, ID_PROFIL_CHAMBRE number(10,0), LONGUEUR number(20,5), COMMUNE number(10,0)
    -> BulkAttributeRenamer
BulkAttributeRenamer
    CASE_CHANGE_TYPE = lowercase
    PATTERN_ACTION_DISP = Change Case
    ATTRCHOICE = All Attributes
    -> sige_assainissement.aw_schact (writer POSTGRES_1)
sige_assainissement.aw_schact (writer POSTGRES_1)
    attributes: fid numeric(10,0), gid numeric(10,0), deleted numeric(1,0), area_nominal numeric(20,8), point_number varchar(50), name varchar(60), sonderbauwerk varchar(20), sbw numeric(20,0), name2 varchar(20), bemerkung varchar(255), f1 varchar(20), f2 varchar(20), f3 varchar(20), tiefe numeric(20,5), baujahr numeric(20,0), dn numeric(20,5), breite numeric(20,5), unten_dn numeric(20,5), unten_breite numeric(20,5), wanddicke numeric(20,5), schachthals varchar(5), anschluesse numeric(20,5), uebergangsplatte varchar(5), abdeckplatte varchar(5), baugrubenbreite numeric(20,5), boeschungswinkel numeric(20,5), flaeche numeric(20,5), ueberstauhaeufigkeit numeric(20,5), letzter_ueberstau date, bezeichnung1 varchar(20),
      bezeichnung2 varchar(20), skalierfaktor numeric(20,5), ortsbezeichnung varchar(50), unten_hoehe numeric(20,5), anzahl_einlaeufe numeric(2,0), anzahl_auslaeufe numeric(2,0), tb_point_number numeric(15,0), komplex_label varchar(2000), id_status numeric(10,0), id_strasse numeric(10,0), id_lage numeric(10,0), id_schachtart numeric(10,0), id_zugaenglichkeit numeric(10,0), id_funktion numeric(10,0), id_material numeric(10,0), id_finanzierungskennziffer numeric(10,0), id_hoehengenauigkeit numeric(10,0), id_lagegenauigkeit numeric(10,0), id_konus_baustoff numeric(10,0), id_oben_baustoff numeric(10,0), id_einstieghilfe numeric(10,0), id_unten_baustoff numeric(10,0), id_gerinne_baustoff numeric(10,0), id_gruendung numeric(10,0), id_schacht_form numeric(10,0), id_unten_form numeric(10,0), id_begr_beschichtung numeric(10,0), id_steigeisengaenge numeric(10,0), id_verkehrsflaeche numeric(10,0), id_gerinne_form numeric(10,0),
      id_nutzungs_art numeric(10,0), id_beschichtung_innen numeric(10,0), id_beschichtung_aussen numeric(10,0), id_eigentumsverhaeltnis numeric(10,0), id_baugrubenform numeric(10,0), fid_ks numeric(10,0), fid_lagebezeichnung numeric(10,0), fid_einrichtungs_typ numeric(10,0), chambre_ancienid varchar(20), fid_collecteur numeric(10,0), id_commune numeric(10,0), chambre_plan varchar(20), id_brisecharge numeric(10,0), id_coupevent numeric(10,0), id_limiteurdebit numeric(10,0), id_profil numeric(10,0), chambre_controle date, chambre_numeroeca varchar(50), chambre_parcelle varchar(20), chambre_classe varchar(50), chambre_type varchar(50), id_aeration numeric(10,0), date_rehabil date, id_profil_chambre numeric(10,0), longueur numeric(20,5), commune numeric(10,0)
Note: chambre geom
SIGE_ASSAINISSEMENT.AW_SCHACHT_GEO (reader ORACLE_NONSPATIAL_1)
    attributes: ID number(10,0), GID number(10,0), ESEQ number(10,0), SEQ number(10,0), ETYPE number(4,0), DA number(10,0), X1 number(20,8), Y1 number(20,8), Z1 number(20,8), CREATION_CODE_XY_1 number(4,0), ORIENTATION number(20,8), AZIMUTH number(20,8), ACCURACY_LEVEL number(20,8), M_DIRECTION number(20,8), M_DISTANCE number(20,8), CALC_CODE number(4,0), CALC_NUMBER number(10,0), AVG_DEV_XY number(20,8), AVG_DEV_Z number(20,8), CREATION_CODE_Z number(4,0), QUALITY number(10,0), SOURCE number(10,0), DELETED number(1,0), X2 number(20,8), Y2 number(20,8), Z2 number(20,8), CREATION_CODE_XY_2 number(4,0), X3 number(20,8), Y3 number(20,8), Z3 number(20,8),
      CREATION_CODE_XY_3 number(4,0), X4 number(20,8), Y4 number(20,8), Z4 number(20,8), CREATION_CODE_XY_4 number(4,0), X5 number(20,8), Y5 number(20,8), Z5 number(20,8), CREATION_CODE_XY_5 number(4,0), SEQ_ETYPE number(4,0), SEQ_PARAM1 number(20,8), SEQ_PARAM2 number(20,8), ORIGIN number(4,0), CLIPPING number(1,0), FID number(10,0), INVISIBLE number(1,0), DIM_X number(20,8), DIM_Y number(20,8), MUTATION_ID_CREATED number(10,0), MUTATION_STATUS_CREATED number(10,0), USER_CREATED varchar2(255), DATE_CREATED date, MUTATION_ID_DELETED number(10,0), MUTATION_STATUS_DELETED number(10,0), USER_DELETED varchar2(255), DATE_DELETED date, MUTATION_ID_MODIFIED number(10,0), USER_MODIFIED varchar2(255), DATE_MODIFIED date, GEO_CONSTRAINT number(1,0),
      AREA number(20,8), TD_POINT_NUMBER number(10,0), TD_LAYER number(10,0), TD_GROUP number(10,0), TD_NUMBER varchar2(50), PERIMETER number(20,8), LABEL_FROM number(10,0), LABEL_TO number(10,0), LABEL_TEXT varchar2(2000), LINEATTRIBUTE_ID number(10,0), SPATIAL_INDEX_100 number(12,0), SPATIAL_INDEX_200 number(12,0), SPATIAL_INDEX_400 number(12,0), TD_DA number(10,0), DTEXT number(1,0), FRAME number(1,0), FIELD_CODE number(4,0), SEQ_PARAM1_2 number(20,8), SEQ_PARAM2_2 number(20,8), SEQ_PARAM1_3 number(20,8), SEQ_PARAM2_3 number(20,8), SEQ_PARAM1_4 number(20,8), SEQ_PARAM2_4 number(20,8), SEQ_PARAM1_5 number(20,8), SEQ_PARAM2_5 number(20,8), SPATIAL_INDEX_25 number(12,0), SPATIAL_INDEX_50 number(12,0), Z_DIFF number(20,8), SEQ_PARAM3 number(20,8), SEQ_PARAM3_2 number(20,8),
      SEQ_PARAM3_3 number(20,8), SEQ_PARAM3_4 number(20,8), SEQ_PARAM3_5 number(20,8), Z_TERRAIN number(20,8), TB_POINT_NUMBER number(15,0)
    -> BulkAttributeRenamer_2
BulkAttributeRenamer_2
    CASE_CHANGE_TYPE = lowercase
    PATTERN_ACTION_DISP = Change Case
    ATTRCHOICE = All Attributes
    -> sige_assainissement.aw_schacht_geo (writer POSTGRES_1)
sige_assainissement.aw_schacht_geo (writer POSTGRES_1)
    attributes: id numeric(10,0), gid numeric(10,0), eseq numeric(10,0), seq numeric(10,0), etype numeric(4,0), da numeric(10,0), x1 numeric(20,8), y1 numeric(20,8), z1 numeric(20,8), creation_code_xy_1 numeric(4,0), orientation numeric(20,8), azimuth numeric(20,8), accuracy_level numeric(20,8), m_direction numeric(20,8), m_distance numeric(20,8), calc_code numeric(4,0), calc_number numeric(10,0), avg_dev_xy numeric(20,8), avg_dev_z numeric(20,8), creation_code_z numeric(4,0), quality numeric(10,0), source numeric(10,0), deleted numeric(1,0), x2 numeric(20,8), y2 numeric(20,8), z2 numeric(20,8), creation_code_xy_2 numeric(4,0), x3 numeric(20,8), y3 numeric(20,8), z3 numeric(20,8),
      creation_code_xy_3 numeric(4,0), x4 numeric(20,8), y4 numeric(20,8), z4 numeric(20,8), creation_code_xy_4 numeric(4,0), x5 numeric(20,8), y5 numeric(20,8), z5 numeric(20,8), creation_code_xy_5 numeric(4,0), seq_etype numeric(4,0), seq_param1 numeric(20,8), seq_param2 numeric(20,8), origin numeric(4,0), clipping numeric(1,0), fid numeric(10,0), invisible numeric(1,0), dim_x numeric(20,8), dim_y numeric(20,8), mutation_id_created numeric(10,0), mutation_status_created numeric(10,0), user_created varchar(255), date_created date, mutation_id_deleted numeric(10,0), mutation_status_deleted numeric(10,0), user_deleted varchar(255), date_deleted date, mutation_id_modified numeric(10,0), user_modified varchar(255), date_modified date, geo_constraint numeric(1,0),
      area numeric(20,8), td_point_number numeric(10,0), td_layer numeric(10,0), td_group numeric(10,0), td_number varchar(50), perimeter numeric(20,8), label_from numeric(10,0), label_to numeric(10,0), label_text varchar(2000), lineattribute_id numeric(10,0), spatial_index_100 numeric(12,0), spatial_index_200 numeric(12,0), spatial_index_400 numeric(12,0), td_da numeric(10,0), dtext numeric(1,0), frame numeric(1,0), field_code numeric(4,0), seq_param1_2 numeric(20,8), seq_param2_2 numeric(20,8), seq_param1_3 numeric(20,8), seq_param2_3 numeric(20,8), seq_param1_4 numeric(20,8), seq_param2_4 numeric(20,8), seq_param1_5 numeric(20,8), seq_param2_5 numeric(20,8), spatial_index_25 numeric(12,0), spatial_index_50 numeric(12,0), z_diff numeric(20,8), seq_param3 numeric(20,8), seq_param3_2 numeric(20,8),
      seq_param3_3 numeric(20,8), seq_param3_4 numeric(20,8), seq_param3_5 numeric(20,8), z_terrain numeric(20,8), tb_point_number numeric(15,0)
Note: couvercle
SIGE_ASSAINISSEMENT.AW_SCHACHT_DECKEL (reader ORACLE_NONSPATIAL_2)
    attributes: FID number(10,0), GID number(10,0), DELETED number(1,0), AREA_NOMINAL number(20,8), POINT_NUMBER varchar2(50), NAME varchar2(60), DECKEL_DN number(20,5), DECKEL_BREITE number(20,5), NR number(20,0), BEZUGSDECKEL number(20,0), SKALIERFAKTOR number(20,5), SONDERBAUWERK_ID number(10,0), F1 varchar2(20), BEMERKUNG varchar2(255), BEZEICHNUNG1 varchar2(20), TB_POINT_NUMBER number(15,0), ID_DECKEL_FORM number(10,0), ID_HOEHENGENAUIGKEIT number(10,0), ID_BELASTUNG number(10,0), ID_MATERIAL number(10,0), ID_KENNUNG number(10,0), ID_LAGEGENAUIGKEIT number(10,0), FID_HERSTELLER number(10,0), FID_SCHACHT number(10,0), FID_SCHACHT2 number(10,0)
    -> BulkAttributeRenamer_3
BulkAttributeRenamer_3
    CASE_CHANGE_TYPE = lowercase
    PATTERN_ACTION_DISP = Change Case
    ATTRCHOICE = All Attributes
    -> sige_assainissement.aw_schacht_deckel (writer POSTGRES_1)
sige_assainissement.aw_schacht_deckel (writer POSTGRES_1)
    attributes: fid numeric(10,0), gid numeric(10,0), deleted numeric(1,0), area_nominal numeric(20,8), point_number varchar(50), name varchar(60), deckel_dn numeric(20,5), deckel_breite numeric(20,5), nr numeric(20,0), bezugsdeckel numeric(20,0), skalierfaktor numeric(20,5), sonderbauwerk_id numeric(10,0), f1 varchar(20), bemerkung varchar(255), bezeichnung1 varchar(20), tb_point_number numeric(15,0), id_deckel_form numeric(10,0), id_hoehengenauigkeit numeric(10,0), id_belastung numeric(10,0), id_material numeric(10,0), id_kennung numeric(10,0), id_lagegenauigkeit numeric(10,0), fid_hersteller numeric(10,0), fid_schacht numeric(10,0), fid_schacht2 numeric(10,0)
Note: couvercle geom
SIGE_ASSAINISSEMENT.AW_SCHACHT_DECKEL_GEO (reader ORACLE_NONSPATIAL_3)
    attributes: ID number(10,0), GID number(10,0), ESEQ number(10,0), SEQ number(10,0), ETYPE number(4,0), DA number(10,0), X1 number(20,8), Y1 number(20,8), Z1 number(20,8), CREATION_CODE_XY_1 number(4,0), ORIENTATION number(20,8), AZIMUTH number(20,8), ACCURACY_LEVEL number(20,8), M_DIRECTION number(20,8), M_DISTANCE number(20,8), CALC_CODE number(4,0), CALC_NUMBER number(10,0), AVG_DEV_XY number(20,8), AVG_DEV_Z number(20,8), CREATION_CODE_Z number(4,0), QUALITY number(10,0), SOURCE number(10,0), DELETED number(1,0), X2 number(20,8), Y2 number(20,8), Z2 number(20,8), CREATION_CODE_XY_2 number(4,0), X3 number(20,8), Y3 number(20,8), Z3 number(20,8),
      CREATION_CODE_XY_3 number(4,0), X4 number(20,8), Y4 number(20,8), Z4 number(20,8), CREATION_CODE_XY_4 number(4,0), X5 number(20,8), Y5 number(20,8), Z5 number(20,8), CREATION_CODE_XY_5 number(4,0), SEQ_ETYPE number(4,0), SEQ_PARAM1 number(20,8), SEQ_PARAM2 number(20,8), ORIGIN number(4,0), CLIPPING number(1,0), FID number(10,0), INVISIBLE number(1,0), DIM_X number(20,8), DIM_Y number(20,8), MUTATION_ID_CREATED number(10,0), MUTATION_STATUS_CREATED number(10,0), USER_CREATED varchar2(255), DATE_CREATED date, MUTATION_ID_DELETED number(10,0), MUTATION_STATUS_DELETED number(10,0), USER_DELETED varchar2(255), DATE_DELETED date, MUTATION_ID_MODIFIED number(10,0), USER_MODIFIED varchar2(255), DATE_MODIFIED date, GEO_CONSTRAINT number(1,0),
      AREA number(20,8), TD_POINT_NUMBER number(10,0), TD_LAYER number(10,0), TD_GROUP number(10,0), TD_NUMBER varchar2(50), PERIMETER number(20,8), LABEL_FROM number(10,0), LABEL_TO number(10,0), LABEL_TEXT varchar2(2000), LINEATTRIBUTE_ID number(10,0), SPATIAL_INDEX_100 number(12,0), SPATIAL_INDEX_200 number(12,0), SPATIAL_INDEX_400 number(12,0), TD_DA number(10,0), DTEXT number(1,0), FRAME number(1,0), FIELD_CODE number(4,0), SEQ_PARAM1_2 number(20,8), SEQ_PARAM2_2 number(20,8), SEQ_PARAM1_3 number(20,8), SEQ_PARAM2_3 number(20,8), SEQ_PARAM1_4 number(20,8), SEQ_PARAM2_4 number(20,8), SEQ_PARAM1_5 number(20,8), SEQ_PARAM2_5 number(20,8), SPATIAL_INDEX_25 number(12,0), SPATIAL_INDEX_50 number(12,0), Z_DIFF number(20,8), SEQ_PARAM3 number(20,8), SEQ_PARAM3_2 number(20,8),
      SEQ_PARAM3_3 number(20,8), SEQ_PARAM3_4 number(20,8), SEQ_PARAM3_5 number(20,8), Z_TERRAIN number(20,8), TB_POINT_NUMBER number(15,0)
    -> BulkAttributeRenamer_4
BulkAttributeRenamer_4
    CASE_CHANGE_TYPE = lowercase
    PATTERN_ACTION_DISP = Change Case
    ATTRCHOICE = All Attributes
    -> sige_assainissement.aw_schacht_deckel_geo (writer POSTGRES_1)
sige_assainissement.aw_schacht_deckel_geo (writer POSTGRES_1)
    attributes: id numeric(10,0), gid numeric(10,0), eseq numeric(10,0), seq numeric(10,0), etype numeric(4,0), da numeric(10,0), x1 numeric(20,8), y1 numeric(20,8), z1 numeric(20,8), creation_code_xy_1 numeric(4,0), orientation numeric(20,8), azimuth numeric(20,8), accuracy_level numeric(20,8), m_direction numeric(20,8), m_distance numeric(20,8), calc_code numeric(4,0), calc_number numeric(10,0), avg_dev_xy numeric(20,8), avg_dev_z numeric(20,8), creation_code_z numeric(4,0), quality numeric(10,0), source numeric(10,0), deleted numeric(1,0), x2 numeric(20,8), y2 numeric(20,8), z2 numeric(20,8), creation_code_xy_2 numeric(4,0), x3 numeric(20,8), y3 numeric(20,8), z3 numeric(20,8),
      creation_code_xy_3 numeric(4,0), x4 numeric(20,8), y4 numeric(20,8), z4 numeric(20,8), creation_code_xy_4 numeric(4,0), x5 numeric(20,8), y5 numeric(20,8), z5 numeric(20,8), creation_code_xy_5 numeric(4,0), seq_etype numeric(4,0), seq_param1 numeric(20,8), seq_param2 numeric(20,8), origin numeric(4,0), clipping numeric(1,0), fid numeric(10,0), invisible numeric(1,0), dim_x numeric(20,8), dim_y numeric(20,8), mutation_id_created numeric(10,0), mutation_status_created numeric(10,0), user_created varchar(255), date_created date, mutation_id_deleted numeric(10,0), mutation_status_deleted numeric(10,0), user_deleted varchar(255), date_deleted date, mutation_id_modified numeric(10,0), user_modified varchar(255), date_modified date, geo_constraint numeric(1,0),
      area numeric(20,8), td_point_number numeric(10,0), td_layer numeric(10,0), td_group numeric(10,0), td_number varchar(50), perimeter numeric(20,8), label_from numeric(10,0), label_to numeric(10,0), label_text varchar(2000), lineattribute_id numeric(10,0), spatial_index_100 numeric(12,0), spatial_index_200 numeric(12,0), spatial_index_400 numeric(12,0), td_da numeric(10,0), dtext numeric(1,0), frame numeric(1,0), field_code numeric(4,0), seq_param1_2 numeric(20,8), seq_param2_2 numeric(20,8), seq_param1_3 numeric(20,8), seq_param2_3 numeric(20,8), seq_param1_4 numeric(20,8), seq_param2_4 numeric(20,8), seq_param1_5 numeric(20,8), seq_param2_5 numeric(20,8), spatial_index_25 numeric(12,0), spatial_index_50 numeric(12,0), z_diff numeric(20,8), seq_param3 numeric(20,8), seq_param3_2 numeric(20,8),
      seq_param3_3 numeric(20,8), seq_param3_4 numeric(20,8), seq_param3_5 numeric(20,8), z_terrain numeric(20,8), tb_point_number numeric(15,0)
SIGE_ASSAINISSEMENT.AW_HALTUNG_BETTUNG_TBD (reader ORACLE_NONSPATIAL_6)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_23
BulkAttributeRenamer_23
    CASE_CHANGE_TYPE = lowercase
    PATTERN_ACTION_DISP = Change Case
    ATTRCHOICE = All Attributes
    -> sige_assainissement.aw_haltung_bettung_tbd (writer POSTGRES_4)
sige_assainissement.aw_haltung_bettung_tbd (writer POSTGRES_4)
    attributes: id numeric(10,0), external_id numeric(10,0), value varchar(255), date_of_creation date, designer varchar(255), commentary varchar(255), active numeric(1,0), short_value varchar(255)
SIGE_ASSAINISSEMENT.AW_HALTUNG_VERB_ART_TBD (reader ORACLE_NONSPATIAL_6)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_27
BulkAttributeRenamer_27
    CASE_CHANGE_TYPE = lowercase
    PATTERN_ACTION_DISP = Change Case
    ATTRCHOICE = All Attributes
    -> sige_assainissement.aw_haltung_verb_art_tbd (writer POSTGRES_4)
sige_assainissement.aw_haltung_verb_art_tbd (writer POSTGRES_4)
    attributes: id numeric(10,0), external_id numeric(10,0), value varchar(255), date_of_creation date, designer varchar(255), commentary varchar(255), active numeric(1,0), short_value varchar(255)
SIGE_ASSAINISSEMENT.AW_HALTUNG_FKT_HIERAR_TBD (reader ORACLE_NONSPATIAL_6)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_26
BulkAttributeRenamer_26
    CASE_CHANGE_TYPE = lowercase
    PATTERN_ACTION_DISP = Change Case
    ATTRCHOICE = All Attributes
    -> sige_assainissement.aw_haltung_fkt_hierar_tbd (writer POSTGRES_4)
sige_assainissement.aw_haltung_fkt_hierar_tbd (writer POSTGRES_4)
    attributes: id numeric(10,0), external_id numeric(10,0), value varchar(255), date_of_creation date, designer varchar(255), commentary varchar(255), active numeric(1,0), short_value varchar(255)
SIGE_ASSAINISSEMENT.AW_HALTUNG_MATERIAL_TBD (reader ORACLE_NONSPATIAL_6)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_25
BulkAttributeRenamer_25
    CASE_CHANGE_TYPE = lowercase
    PATTERN_ACTION_DISP = Change Case
    ATTRCHOICE = All Attributes
    -> sige_assainissement.aw_haltung_material_tbd (writer POSTGRES_4)
sige_assainissement.aw_haltung_material_tbd (writer POSTGRES_4)
    attributes: id numeric(10,0), external_id numeric(10,0), value varchar(255), date_of_creation date, designer varchar(255), commentary varchar(255), active numeric(1,0), short_value varchar(255)
SIGE_ASSAINISSEMENT.AW_HALTUNG_FKT_HYDRAU_TBD (reader ORACLE_NONSPATIAL_6)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_24
BulkAttributeRenamer_24
    CASE_CHANGE_TYPE = lowercase
    PATTERN_ACTION_DISP = Change Case
    ATTRCHOICE = All Attributes
    -> sige_assainissement.aw_haltung_fkt_hydrau_tbd (writer POSTGRES_4)
sige_assainissement.aw_haltung_fkt_hydrau_tbd (writer POSTGRES_4)
    attributes: id numeric(10,0), external_id numeric(10,0), value varchar(255), date_of_creation date, designer varchar(255), commentary varchar(255), active numeric(1,0), short_value varchar(255)
Note: collecteur
SIGE_ASSAINISSEMENT.AW_HALTUNG (reader ORACLE_NONSPATIAL_1)
    attributes: FID number(10,0), GID number(10,0), DELETED number(1,0), AREA_NOMINAL number(20,8), NAME varchar2(130), NAME2 varchar2(130), BEMERKUNG varchar2(255), DATEI varchar2(80), F1 varchar2(20), F2 varchar2(20), F3 varchar2(20), ABSTURZ number(20,0), SOHLSPRUNG number(20,0), PROFIL_BREITE number(20,5), PROFIL_HOEHE number(20,5), HALTUNGSLAENGE number(20,5), STRANGLAENGE number(20,5), LAENGEN_HERKUNFT varchar2(5), ROHRLAENGE number(20,5), BAUJAHR number(20,0), RADIUS number(20,5), KB_WERT_GMS number(20,5), KB_WERT_PC number(20,5), GEFAELLE number(20,5), GEFAELLE_HERKUNFT varchar2(5), STRANG_GEFAELLE number(20,5), HALTUNGSFLAECHE number(20,5), WARTUNGSINTERVALL_J number(20,5), WARTUNGSINTERVALL_M number(20,5), LETZTE_WARTUNG date,
      RATTENBEFALL number(20,0), RATTENBEKAEMPFUNG date, ANSCHAFFUNGSWERT number(20,5), NUTZUNGSDAUER number(20,5), EINSTAUHAEUFIGKEIT number(20,5), LETZTER_EINSTAU date, WASSERRECHTE varchar2(30), FLIESS_PFEIL varchar2(40), FLIESS_PFEIL_WINKEL number(20,5), EINLAUF_TIEFE number(20,5), AUSLAUF_TIEFE number(20,5), BEZEICHNUNG1 varchar2(40), BEZEICHNUNG2 varchar2(40), BEZEICHNUNG3 varchar2(40), STRANGLAENGE_HOR number(20,5), ABSTURZ_HOEHE number(20,5), SOHLSPRUNG_HOEHE number(20,5), MITTLERE_TIEFE number(20,5), EINLAUF_TEXT varchar2(5), AUSLAUF_TEXT varchar2(5), GEP_ANSCHRIEB number(10,0), PROFIL_BREITE_ALT number(10,5), GEFAELLE_ALT number(10,5), DIST_VS_E number(20,8), DIST_BS_A number(20,8), ID_STRASSE number(10,0), ID_PROFILART number(10,0), ID_STATUS number(10,0), ID_NUTZUNGS_ART number(10,0), ID_PROFILEINBAUTEN number(10,0),
      ID_VERBINDUNGSART number(10,0), ID_VERLEGEART number(10,0), ID_MATERIAL number(10,0), ID_BESCHICHTUNG_INNEN number(10,0), ID_BESCHICHTUNG_AUSSEN number(10,0), ID_EIGENTUMSVERHAELTNIS number(10,0), ID_BEWERT_FAKTOR_Q number(10,0), ID_FINANZIERUNGSKENNZIFFER number(10,0), ID_ABWASSER_ART number(10,0), ID_LAGE number(10,0), ID_WASSERSCHUTZZONE number(10,0), ID_BODENART number(10,0), ID_BETTUNG number(10,0), ID_GRUNDWASSERABSTAND number(10,0), ID_FUNKTION_HIERARCH number(10,0), ID_FUNKTION_HYDRAU number(10,0), ID_HOEHENGENAUIGKEIT number(10,0), ID_DICHTUNGSART number(10,0), ID_BEGR_BESCHICHTUNG number(10,0), ID_LAGEGENAUIGKEIT number(10,0), FID_KANAL number(10,0), FID_LAGEBEZEICHNUNG number(10,0), FID_VS number(10,0), FID_BS number(10,0), FID_EZG number(10,0), FID_EINRICHTUNGS_TYP number(10,0), KANALSYSTEM varchar2(1), RESTBUCHWERT number(10,2), RESTNUTZUNGSDAUER number(10,2), ABSCHREIB_ANTEIL number(10,4),
      CANALISATION_ANCIENID varchar2(100), CANALISATION_ANCIENCOLLAVAL varchar2(50), CANALISATION_ANCIENPTAVAL varchar2(50), CANALISATION_ANCIENCOLLAMONT varchar2(50), CANALISATION_ANCIENPTAMONT varchar2(50), ID_COMMUNE number(10,0), CANALISATION_PLAN varchar2(20), ID_POSITIONAVAL number(10,0), ID_POSITIONAMONT number(10,0), DATE_REHABIL date, NUMERO varchar2(10), ANNÉE_RÉHABIL number(4,0), COMMUNE number(10,0)
    -> BulkAttributeRenamer_5
BulkAttributeRenamer_5
    CASE_CHANGE_TYPE = lowercase
    PATTERN_ACTION_DISP = Change Case
    ATTRCHOICE = All Attributes
    -> sige_assainissement.aw_haltung (writer POSTGRES_2)
sige_assainissement.aw_haltung (writer POSTGRES_2)
    attributes: fid numeric(10,0), gid numeric(10,0), deleted numeric(1,0), area_nominal numeric(20,8), name varchar(130), name2 varchar(130), bemerkung varchar(255), datei varchar(80), f1 varchar(20), f2 varchar(20), f3 varchar(20), absturz numeric(20,0), sohlsprung numeric(20,0), profil_breite numeric(20,5), profil_hoehe numeric(20,5), haltungslaenge numeric(20,5), stranglaenge numeric(20,5), laengen_herkunft varchar(5), rohrlaenge numeric(20,5), baujahr numeric(20,0), radius numeric(20,5), kb_wert_gms numeric(20,5), kb_wert_pc numeric(20,5), gefaelle numeric(20,5), gefaelle_herkunft varchar(5), strang_gefaelle numeric(20,5), haltungsflaeche numeric(20,5), wartungsintervall_j numeric(20,5), wartungsintervall_m numeric(20,5), letzte_wartung date,
      rattenbefall numeric(20,0), rattenbekaempfung date, anschaffungswert numeric(20,5), nutzungsdauer numeric(20,5), einstauhaeufigkeit numeric(20,5), letzter_einstau date, wasserrechte varchar(30), fliess_pfeil varchar(40), fliess_pfeil_winkel numeric(20,5), einlauf_tiefe numeric(20,5), auslauf_tiefe numeric(20,5), bezeichnung1 varchar(40), bezeichnung2 varchar(40), bezeichnung3 varchar(40), stranglaenge_hor numeric(20,5), absturz_hoehe numeric(20,5), sohlsprung_hoehe numeric(20,5), mittlere_tiefe numeric(20,5), einlauf_text varchar(5), auslauf_text varchar(5), gep_anschrieb numeric(10,0), profil_breite_alt numeric(10,5), gefaelle_alt numeric(10,5), dist_vs_e numeric(20,8), dist_bs_a numeric(20,8), id_strasse numeric(10,0), id_profilart numeric(10,0), id_status numeric(10,0), id_nutzungs_art numeric(10,0), id_profileinbauten numeric(10,0),
      id_verbindungsart numeric(10,0), id_verlegeart numeric(10,0), id_material numeric(10,0), id_beschichtung_innen numeric(10,0), id_beschichtung_aussen numeric(10,0), id_eigentumsverhaeltnis numeric(10,0), id_bewert_faktor_q numeric(10,0), id_finanzierungskennziffer numeric(10,0), id_abwasser_art numeric(10,0), id_lage numeric(10,0), id_wasserschutzzone numeric(10,0), id_bodenart numeric(10,0), id_bettung numeric(10,0), id_grundwasserabstand numeric(10,0), id_funktion_hierarch numeric(10,0), id_funktion_hydrau numeric(10,0), id_hoehengenauigkeit numeric(10,0), id_dichtungsart numeric(10,0), id_begr_beschichtung numeric(10,0), id_lagegenauigkeit numeric(10,0), fid_kanal numeric(10,0), fid_lagebezeichnung numeric(10,0), fid_vs numeric(10,0), fid_bs numeric(10,0), fid_ezg numeric(10,0), fid_einrichtungs_typ numeric(10,0), kanalsystem varchar(1), restbuchwert numeric(10,2), restnutzungsdauer numeric(10,2), abschreib_anteil numeric(10,4),
      canalisation_ancienid varchar(100), canalisation_anciencollaval varchar(50), canalisation_ancienptaval varchar(50), canalisation_anciencollamont varchar(50), canalisation_ancienptamont varchar(50), id_commune numeric(10,0), canalisation_plan varchar(20), id_positionaval numeric(10,0), id_positionamont numeric(10,0), date_rehabil date, numero varchar(10), année_réhabil numeric(4,0), commune numeric(10,0)
Note: collecteur geom
SIGE_ASSAINISSEMENT.AW_HALTUNG_GEO (reader ORACLE_NONSPATIAL_1)
    attributes: ID number(10,0), GID number(10,0), ESEQ number(10,0), SEQ number(10,0), ETYPE number(4,0), DA number(10,0), X1 number(20,8), Y1 number(20,8), Z1 number(20,8), CREATION_CODE_XY_1 number(4,0), ORIENTATION number(20,8), AZIMUTH number(20,8), ACCURACY_LEVEL number(20,8), M_DIRECTION number(20,8), M_DISTANCE number(20,8), CALC_CODE number(4,0), CALC_NUMBER number(10,0), AVG_DEV_XY number(20,8), AVG_DEV_Z number(20,8), CREATION_CODE_Z number(4,0), QUALITY number(10,0), SOURCE number(10,0), DELETED number(1,0), X2 number(20,8), Y2 number(20,8), Z2 number(20,8), CREATION_CODE_XY_2 number(4,0), X3 number(20,8), Y3 number(20,8), Z3 number(20,8),
      CREATION_CODE_XY_3 number(4,0), X4 number(20,8), Y4 number(20,8), Z4 number(20,8), CREATION_CODE_XY_4 number(4,0), X5 number(20,8), Y5 number(20,8), Z5 number(20,8), CREATION_CODE_XY_5 number(4,0), SEQ_ETYPE number(4,0), SEQ_PARAM1 number(20,8), SEQ_PARAM2 number(20,8), ORIGIN number(4,0), CLIPPING number(1,0), FID number(10,0), INVISIBLE number(1,0), DIM_X number(20,8), DIM_Y number(20,8), MUTATION_ID_CREATED number(10,0), MUTATION_STATUS_CREATED number(10,0), USER_CREATED varchar2(255), DATE_CREATED date, MUTATION_ID_DELETED number(10,0), MUTATION_STATUS_DELETED number(10,0), USER_DELETED varchar2(255), DATE_DELETED date, MUTATION_ID_MODIFIED number(10,0), USER_MODIFIED varchar2(255), DATE_MODIFIED date, GEO_CONSTRAINT number(1,0),
      AREA number(20,8), TD_POINT_NUMBER number(10,0), TD_LAYER number(10,0), TD_GROUP number(10,0), TD_NUMBER varchar2(50), PERIMETER number(20,8), LABEL_FROM number(10,0), LABEL_TO number(10,0), LABEL_TEXT varchar2(2000), LINEATTRIBUTE_ID number(10,0), SPATIAL_INDEX_100 number(12,0), SPATIAL_INDEX_200 number(12,0), SPATIAL_INDEX_400 number(12,0), TD_DA number(10,0), DTEXT number(1,0), FRAME number(1,0), FIELD_CODE number(4,0), SEQ_PARAM1_2 number(20,8), SEQ_PARAM2_2 number(20,8), SEQ_PARAM1_3 number(20,8), SEQ_PARAM2_3 number(20,8), SEQ_PARAM1_4 number(20,8), SEQ_PARAM2_4 number(20,8), SEQ_PARAM1_5 number(20,8), SEQ_PARAM2_5 number(20,8), SPATIAL_INDEX_25 number(12,0), SPATIAL_INDEX_50 number(12,0), Z_DIFF number(20,8), SEQ_PARAM3 number(20,8), SEQ_PARAM3_2 number(20,8),
      SEQ_PARAM3_3 number(20,8), SEQ_PARAM3_4 number(20,8), SEQ_PARAM3_5 number(20,8), Z_TERRAIN number(20,8), TB_POINT_NUMBER number(15,0)
    -> BulkAttributeRenamer_6
BulkAttributeRenamer_6
    CASE_CHANGE_TYPE = lowercase
    PATTERN_ACTION_DISP = Change Case
    ATTRCHOICE = All Attributes
    -> sige_assainissement.aw_haltung_geo (writer POSTGRES_2)
sige_assainissement.aw_haltung_geo (writer POSTGRES_2)
    attributes: id numeric(10,0), gid numeric(10,0), eseq numeric(10,0), seq numeric(10,0), etype numeric(4,0), da numeric(10,0), x1 numeric(20,8), y1 numeric(20,8), z1 numeric(20,8), creation_code_xy_1 numeric(4,0), orientation numeric(20,8), azimuth numeric(20,8), accuracy_level numeric(20,8), m_direction numeric(20,8), m_distance numeric(20,8), calc_code numeric(4,0), calc_number numeric(10,0), avg_dev_xy numeric(20,8), avg_dev_z numeric(20,8), creation_code_z numeric(4,0), quality numeric(10,0), source numeric(10,0), deleted numeric(1,0), x2 numeric(20,8), y2 numeric(20,8), z2 numeric(20,8), creation_code_xy_2 numeric(4,0), x3 numeric(20,8), y3 numeric(20,8), z3 numeric(20,8),
      creation_code_xy_3 numeric(4,0), x4 numeric(20,8), y4 numeric(20,8), z4 numeric(20,8), creation_code_xy_4 numeric(4,0), x5 numeric(20,8), y5 numeric(20,8), z5 numeric(20,8), creation_code_xy_5 numeric(4,0), seq_etype numeric(4,0), seq_param1 numeric(20,8), seq_param2 numeric(20,8), origin numeric(4,0), clipping numeric(1,0), fid numeric(10,0), invisible numeric(1,0), dim_x numeric(20,8), dim_y numeric(20,8), mutation_id_created numeric(10,0), mutation_status_created numeric(10,0), user_created varchar(255), date_created date, mutation_id_deleted numeric(10,0), mutation_status_deleted numeric(10,0), user_deleted varchar(255), date_deleted date, mutation_id_modified numeric(10,0), user_modified varchar(255), date_modified date, geo_constraint numeric(1,0),
      area numeric(20,8), td_point_number numeric(10,0), td_layer numeric(10,0), td_group numeric(10,0), td_number varchar(50), perimeter numeric(20,8), label_from numeric(10,0), label_to numeric(10,0), label_text varchar(2000), lineattribute_id numeric(10,0), spatial_index_100 numeric(12,0), spatial_index_200 numeric(12,0), spatial_index_400 numeric(12,0), td_da numeric(10,0), dtext numeric(1,0), frame numeric(1,0), field_code numeric(4,0), seq_param1_2 numeric(20,8), seq_param2_2 numeric(20,8), seq_param1_3 numeric(20,8), seq_param2_3 numeric(20,8), seq_param1_4 numeric(20,8), seq_param2_4 numeric(20,8), seq_param1_5 numeric(20,8), seq_param2_5 numeric(20,8), spatial_index_25 numeric(12,0), spatial_index_50 numeric(12,0), z_diff numeric(20,8), seq_param3 numeric(20,8), seq_param3_2 numeric(20,8),
      seq_param3_3 numeric(20,8), seq_param3_4 numeric(20,8), seq_param3_5 numeric(20,8), z_terrain numeric(20,8), tb_point_number numeric(15,0)
SIGE_ASSAINISSEMENT.AW_SCHACHT_EINST_HILFE_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_14
BulkAttributeRenamer_14
    CASE_CHANGE_TYPE = lowercase
    PATTERN_ACTION_DISP = Change Case
    ATTRCHOICE = All Attributes
    -> sige_assainissement.aw_schacht_einst_hilfe_tbd (writer POSTGRES_3)
sige_assainissement.aw_schacht_einst_hilfe_tbd (writer POSTGRES_3)
    attributes: id numeric(10,0), external_id numeric(10,0), value varchar(255), date_of_creation date, designer varchar(255), commentary varchar(255), active numeric(1,0), short_value varchar(255)
SIGE_ASSAINISSEMENT.AW_SCHACHT_UNTENFORM_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_18
BulkAttributeRenamer_18
    CASE_CHANGE_TYPE = lowercase
    PATTERN_ACTION_DISP = Change Case
    ATTRCHOICE = All Attributes
    -> sige_assainissement.aw_schacht_untenform_tbd (writer POSTGRES_3)
sige_assainissement.aw_schacht_untenform_tbd (writer POSTGRES_3)
    attributes: id numeric(10,0), external_id numeric(10,0), value varchar(255), date_of_creation date, designer varchar(255), commentary varchar(255), active numeric(1,0), short_value varchar(255)
SIGE_ASSAINISSEMENT.AW_LAGEGENAUIGKEIT_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_19
BulkAttributeRenamer_19
    CASE_CHANGE_TYPE = lowercase
    PATTERN_ACTION_DISP = Change Case
    ATTRCHOICE = All Attributes
    -> sige_assainissement.aw_lagegenauigkeit_tbd (writer POSTGRES_3)
sige_assainissement.aw_lagegenauigkeit_tbd (writer POSTGRES_3)
    attributes: id numeric(10,0), external_id numeric(10,0), value varchar(255), date_of_creation date, designer varchar(255), commentary varchar(255), active numeric(1,0), short_value varchar(255)
SIGE_ASSAINISSEMENT.AW_BESCHICHTUNG_AUSSEN_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_17
BulkAttributeRenamer_17
    CASE_CHANGE_TYPE = lowercase
    PATTERN_ACTION_DISP = Change Case
    ATTRCHOICE = All Attributes
    -> sige_assainissement.aw_beschichtung_aussen_tbd (writer POSTGRES_3)
sige_assainissement.aw_beschichtung_aussen_tbd (writer POSTGRES_3)
    attributes: id numeric(10,0), external_id numeric(10,0), value varchar(255), date_of_creation date, designer varchar(255), commentary varchar(255), active numeric(1,0), short_value varchar(255)
SIGE_ASSAINISSEMENT.AW_ZUGAENGLICHKEIT_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_16
BulkAttributeRenamer_16
    CASE_CHANGE_TYPE = lowercase
    PATTERN_ACTION_DISP = Change Case
    ATTRCHOICE = All Attributes
    -> sige_assainissement.aw_zugaenglichkeit_tbd (writer POSTGRES_3)
sige_assainissement.aw_zugaenglichkeit_tbd (writer POSTGRES_3)
    attributes: id numeric(10,0), external_id numeric(10,0), value varchar(255), date_of_creation date, designer varchar(255), commentary varchar(255), active numeric(1,0), short_value varchar(255)
SIGE_ASSAINISSEMENT.AW_SCHACHT_MATERIAL_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_7
BulkAttributeRenamer_7
    CASE_CHANGE_TYPE = lowercase
    PATTERN_ACTION_DISP = Change Case
    ATTRCHOICE = All Attributes
    -> sige_assainissement.aw_schacht_material_tbd (writer POSTGRES_3)
sige_assainissement.aw_schacht_material_tbd (writer POSTGRES_3)
    attributes: id numeric(10,0), external_id numeric(10,0), value varchar(255), date_of_creation date, designer varchar(255), commentary varchar(255), active numeric(1,0), short_value varchar(255)
SIGE_ASSAINISSEMENT.BA_EIGENTUMSVERHAELTNIS_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_8
BulkAttributeRenamer_8
    CASE_CHANGE_TYPE = lowercase
    PATTERN_ACTION_DISP = Change Case
    ATTRCHOICE = All Attributes
    -> sige_assainissement.ba_eigentumsverhaeltnis_tbd (writer POSTGRES_3)
sige_assainissement.ba_eigentumsverhaeltnis_tbd (writer POSTGRES_3)
    attributes: id numeric(10,0), external_id numeric(10,0), value varchar(255), date_of_creation date, designer varchar(255), commentary varchar(255), active numeric(1,0), short_value varchar(255)
SIGE_ASSAINISSEMENT.AW_SCHACHT_FORM_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_9
BulkAttributeRenamer_9
    CASE_CHANGE_TYPE = lowercase
    PATTERN_ACTION_DISP = Change Case
    ATTRCHOICE = All Attributes
    -> sige_assainissement.aw_schacht_form_tbd (writer POSTGRES_3)
sige_assainissement.aw_schacht_form_tbd (writer POSTGRES_3)
    attributes: id numeric(10,0), external_id numeric(10,0), value varchar(255), date_of_creation date, designer varchar(255), commentary varchar(255), active numeric(1,0), short_value varchar(255)
SIGE_ASSAINISSEMENT.AW_NUTZUNGS_ART_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_11
BulkAttributeRenamer_11
    CASE_CHANGE_TYPE = lowercase
    PATTERN_ACTION_DISP = Change Case
    ATTRCHOICE = All Attributes
    -> sige_assainissement.aw_nutzungs_art_tbd (writer POSTGRES_3)
sige_assainissement.aw_nutzungs_art_tbd (writer POSTGRES_3)
    attributes: id numeric(10,0), external_id numeric(10,0), value varchar(255), date_of_creation date, designer varchar(255), commentary varchar(255), active numeric(1,0), short_value varchar(255)
SIGE_ASSAINISSEMENT.AW_SCHACHT_ART_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_10
BulkAttributeRenamer_10
    CASE_CHANGE_TYPE = lowercase
    PATTERN_ACTION_DISP = Change Case
    ATTRCHOICE = All Attributes
    -> sige_assainissement.aw_schacht_art_tbd (writer POSTGRES_3)
sige_assainissement.aw_schacht_art_tbd (writer POSTGRES_3)
    attributes: id numeric(10,0), external_id numeric(10,0), value varchar(255), date_of_creation date, designer varchar(255), commentary varchar(255), active numeric(1,0), short_value varchar(255)
SIGE_ASSAINISSEMENT.AW_BESCHICHTUNG_INNEN_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_20
BulkAttributeRenamer_20
    CASE_CHANGE_TYPE = lowercase
    PATTERN_ACTION_DISP = Change Case
    ATTRCHOICE = All Attributes
    -> sige_assainissement.aw_beschichtung_innen_tbd (writer POSTGRES_3)
sige_assainissement.aw_beschichtung_innen_tbd (writer POSTGRES_3)
    attributes: id numeric(10,0), external_id numeric(10,0), value varchar(255), date_of_creation date, designer varchar(255), commentary varchar(255), active numeric(1,0), short_value varchar(255)
SIGE_ASSAINISSEMENT.AW_PROFILART_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_12
BulkAttributeRenamer_12
    CASE_CHANGE_TYPE = lowercase
    PATTERN_ACTION_DISP = Change Case
    ATTRCHOICE = All Attributes
    -> sige_assainissement.aw_profilart_tbd (writer POSTGRES_3)
sige_assainissement.aw_profilart_tbd (writer POSTGRES_3)
    attributes: id numeric(10,0), external_id numeric(10,0), value varchar(255), date_of_creation date, designer varchar(255), commentary varchar(255), active numeric(1,0), short_value varchar(255)
SIGE_ASSAINISSEMENT.AW_HOEHENGENAUIGKEIT_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_13
BulkAttributeRenamer_13
    CASE_CHANGE_TYPE = lowercase
    PATTERN_ACTION_DISP = Change Case
    ATTRCHOICE = All Attributes
    -> sige_assainissement.aw_hoehengenauigkeit_tbd (writer POSTGRES_3)
sige_assainissement.aw_hoehengenauigkeit_tbd (writer POSTGRES_3)
    attributes: id numeric(10,0), external_id numeric(10,0), value varchar(255), date_of_creation date, designer varchar(255), commentary varchar(255), active numeric(1,0), short_value varchar(255)
SIGE_ASSAINISSEMENT.BA_STATUS_TBD (reader ORACLE_NONSPATIAL_4)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_15
BulkAttributeRenamer_15
    CASE_CHANGE_TYPE = lowercase
    PATTERN_ACTION_DISP = Change Case
    ATTRCHOICE = All Attributes
    -> sige_assainissement.ba_status_tbd (writer POSTGRES_3)
sige_assainissement.ba_status_tbd (writer POSTGRES_3)
    attributes: id numeric(10,0), external_id numeric(10,0), value varchar(255), date_of_creation date, designer varchar(255), commentary varchar(255), active numeric(1,0), short_value varchar(255)
SIGE_ASSAINISSEMENT.AW_SCHACHTDECKELFORM_TBD (reader ORACLE_NONSPATIAL_5)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_21
BulkAttributeRenamer_21
    CASE_CHANGE_TYPE = lowercase
    PATTERN_ACTION_DISP = Change Case
    ATTRCHOICE = All Attributes
    -> sige_assainissement.aw_schachtdeckelform_tbd (writer POSTGRES_1)
sige_assainissement.aw_schachtdeckelform_tbd (writer POSTGRES_1)
    attributes: id numeric(10,0), external_id numeric(10,0), value varchar(255), date_of_creation date, designer varchar(255), commentary varchar(255), active numeric(1,0), short_value varchar(255)
SIGE_ASSAINISSEMENT.AW_SCHACHT_DECKEL_KNG_TBD (reader ORACLE_NONSPATIAL_5)
    attributes: ID number(10,0), EXTERNAL_ID number(10,0), VALUE varchar2(255), DATE_OF_CREATION date, DESIGNER varchar2(255), COMMENTARY varchar2(255), ACTIVE number(1,0), SHORT_VALUE varchar2(255)
    -> BulkAttributeRenamer_22
BulkAttributeRenamer_22
    CASE_CHANGE_TYPE = lowercase
    PATTERN_ACTION_DISP = Change Case
    ATTRCHOICE = All Attributes
    -> sige_assainissement.aw_schacht_deckel_kng_tbd (writer POSTGRES_1)
sige_assainissement.aw_schacht_deckel_kng_tbd (writer POSTGRES_1)
    attributes: id numeric(10,0), external_id numeric(10,0), value varchar(255), date_of_creation date, designer varchar(255), commentary varchar(255), active numeric(1,0), short_value varchar(255)
SIGE_ASSAINISSEMENT.AW_NETZLINIE (reader ORACLE_NONSPATIAL_7)
    attributes: FID number(10,0), GID number(10,0), DELETED number(1,0), AREA_NOMINAL number(20,8)
    -> BulkAttributeRenamer_28
BulkAttributeRenamer_28
    CASE_CHANGE_TYPE = lowercase
    PATTERN_ACTION_DISP = Change Case
    ATTRCHOICE = All Attributes
    -> sige_assainissement.aw_netzlinie (writer POSTGRES_5)
sige_assainissement.aw_netzlinie (writer POSTGRES_5)
    attributes: fid numeric(10,0), gid numeric(10,0), deleted numeric(1,0), area_nominal numeric(20,8)
SIGE_ASSAINISSEMENT.AW_NETZLINIE_GEO (reader ORACLE_NONSPATIAL_7)
    attributes: ID number(10,0), GID number(10,0), ESEQ number(10,0), SEQ number(10,0), ETYPE number(4,0), DA number(10,0), X1 number(20,8), Y1 number(20,8), Z1 number(20,8), CREATION_CODE_XY_1 number(4,0), ORIENTATION number(20,8), AZIMUTH number(20,8), ACCURACY_LEVEL number(20,8), M_DIRECTION number(20,8), M_DISTANCE number(20,8), CALC_CODE number(4,0), CALC_NUMBER number(10,0), AVG_DEV_XY number(20,8), AVG_DEV_Z number(20,8), CREATION_CODE_Z number(4,0), QUALITY number(10,0), SOURCE number(10,0), DELETED number(1,0), X2 number(20,8), Y2 number(20,8), Z2 number(20,8), CREATION_CODE_XY_2 number(4,0), X3 number(20,8), Y3 number(20,8), Z3 number(20,8),
      CREATION_CODE_XY_3 number(4,0), X4 number(20,8), Y4 number(20,8), Z4 number(20,8), CREATION_CODE_XY_4 number(4,0), X5 number(20,8), Y5 number(20,8), Z5 number(20,8), CREATION_CODE_XY_5 number(4,0), SEQ_ETYPE number(4,0), SEQ_PARAM1 number(20,8), SEQ_PARAM2 number(20,8), ORIGIN number(4,0), CLIPPING number(1,0), FID number(10,0), INVISIBLE number(1,0), DIM_X number(20,8), DIM_Y number(20,8), MUTATION_ID_CREATED number(10,0), MUTATION_STATUS_CREATED number(10,0), USER_CREATED varchar2(255), DATE_CREATED date, MUTATION_ID_DELETED number(10,0), MUTATION_STATUS_DELETED number(10,0), USER_DELETED varchar2(255), DATE_DELETED date, MUTATION_ID_MODIFIED number(10,0), USER_MODIFIED varchar2(255), DATE_MODIFIED date, GEO_CONSTRAINT number(1,0),
      AREA number(20,8), TD_POINT_NUMBER number(10,0), TD_LAYER number(10,0), TD_GROUP number(10,0), TD_NUMBER varchar2(50), PERIMETER number(20,8), LABEL_FROM number(10,0), LABEL_TO number(10,0), LABEL_TEXT varchar2(2000), LINEATTRIBUTE_ID number(10,0), SPATIAL_INDEX_100 number(12,0), SPATIAL_INDEX_200 number(12,0), SPATIAL_INDEX_400 number(12,0), TD_DA number(10,0), DTEXT number(1,0), FRAME number(1,0), FIELD_CODE number(4,0), SEQ_PARAM1_2 number(20,8), SEQ_PARAM2_2 number(20,8), SEQ_PARAM1_3 number(20,8), SEQ_PARAM2_3 number(20,8), SEQ_PARAM1_4 number(20,8), SEQ_PARAM2_4 number(20,8), SEQ_PARAM1_5 number(20,8), SEQ_PARAM2_5 number(20,8), SPATIAL_INDEX_25 number(12,0), SPATIAL_INDEX_50 number(12,0), Z_DIFF number(20,8), SEQ_PARAM3 number(20,8), SEQ_PARAM3_2 number(20,8),
      SEQ_PARAM3_3 number(20,8), SEQ_PARAM3_4 number(20,8), SEQ_PARAM3_5 number(20,8), Z_TERRAIN number(20,8), TB_POINT_NUMBER number(15,0)
    -> BulkAttributeRenamer_29
BulkAttributeRenamer_29
    CASE_CHANGE_TYPE = lowercase
    PATTERN_ACTION_DISP = Change Case
    ATTRCHOICE = All Attributes
    -> sige_assainissement.aw_netzlinie_geo (writer POSTGRES_5)
sige_assainissement.aw_netzlinie_geo (writer POSTGRES_5)
    attributes: id numeric(10,0), gid numeric(10,0), eseq numeric(10,0), seq numeric(10,0), etype numeric(4,0), da numeric(10,0), x1 numeric(20,8), y1 numeric(20,8), z1 numeric(20,8), creation_code_xy_1 numeric(4,0), orientation numeric(20,8), azimuth numeric(20,8), accuracy_level numeric(20,8), m_direction numeric(20,8), m_distance numeric(20,8), calc_code numeric(4,0), calc_number numeric(10,0), avg_dev_xy numeric(20,8), avg_dev_z numeric(20,8), creation_code_z numeric(4,0), quality numeric(10,0), source numeric(10,0), deleted numeric(1,0), x2 numeric(20,8), y2 numeric(20,8), z2 numeric(20,8), creation_code_xy_2 numeric(4,0), x3 numeric(20,8), y3 numeric(20,8), z3 numeric(20,8),
      creation_code_xy_3 numeric(4,0), x4 numeric(20,8), y4 numeric(20,8), z4 numeric(20,8), creation_code_xy_4 numeric(4,0), x5 numeric(20,8), y5 numeric(20,8), z5 numeric(20,8), creation_code_xy_5 numeric(4,0), seq_etype numeric(4,0), seq_param1 numeric(20,8), seq_param2 numeric(20,8), origin numeric(4,0), clipping numeric(1,0), fid numeric(10,0), invisible numeric(1,0), dim_x numeric(20,8), dim_y numeric(20,8), mutation_id_created numeric(10,0), mutation_status_created numeric(10,0), user_created varchar(255), date_created date, mutation_id_deleted numeric(10,0), mutation_status_deleted numeric(10,0), user_deleted varchar(255), date_deleted date, mutation_id_modified numeric(10,0), user_modified varchar(255), date_modified date, geo_constraint numeric(1,0),
      area numeric(20,8), td_point_number numeric(10,0), td_layer numeric(10,0), td_group numeric(10,0), td_number varchar(50), perimeter numeric(20,8), label_from numeric(10,0), label_to numeric(10,0), label_text varchar(2000), lineattribute_id numeric(10,0), spatial_index_100 numeric(12,0), spatial_index_200 numeric(12,0), spatial_index_400 numeric(12,0), td_da numeric(10,0), dtext numeric(1,0), frame numeric(1,0), field_code numeric(4,0), seq_param1_2 numeric(20,8), seq_param2_2 numeric(20,8), seq_param1_3 numeric(20,8), seq_param2_3 numeric(20,8), seq_param1_4 numeric(20,8), seq_param2_4 numeric(20,8), seq_param1_5 numeric(20,8), seq_param2_5 numeric(20,8), spatial_index_25 numeric(12,0), spatial_index_50 numeric(12,0), z_diff numeric(20,8), seq_param3 numeric(20,8), seq_param3_2 numeric(20,8),
      seq_param3_3 numeric(20,8), seq_param3_4 numeric(20,8), seq_param3_5 numeric(20,8), z_terrain numeric(20,8), tb_point_number numeric(15,0)
