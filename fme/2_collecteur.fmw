FME workspace 2_collecteur.fmw

Parameters:
- DestDataset_POSTGRES = sige@172.24.171.203:5432/qgep   # Connection
- SourceDataset_ORACLE_NONSPATIAL_6 = SYSTEM@orcl   # Connection
- DestDataset_POSTGRES_3 = sige@172.24.171.203:5432/qgep   # Connection

Readers:
- ORACLE_NONSPATIAL_1: ORACLE_NONSPATIAL from $(SourceDataset_ORACLE_NONSPATIAL_6)

Writers:
- POSTGRES_1: POSTGRES to $(DestDataset_POSTGRES)
- POSTGRES_2: POSTGRES to $(DestDataset_POSTGRES_3)

Note: collecteur
SIGE_ASSAINISSEMENT.AW_HALTUNG (reader ORACLE_NONSPATIAL_1)
    attributes: FID number(10,0), GID number(10,0), DELETED number(1,0), AREA_NOMINAL number(20,8), NAME varchar2(130), NAME2 varchar2(130), BEMERKUNG varchar2(255), DATEI varchar2(80), F1 varchar2(20), F2 varchar2(20), F3 varchar2(20), ABSTURZ number(20,0), SOHLSPRUNG number(20,0), PROFIL_BREITE number(20,5), PROFIL_HOEHE number(20,5), HALTUNGSLAENGE number(20,5), STRANGLAENGE number(20,5), LAENGEN_HERKUNFT varchar2(5), ROHRLAENGE number(20,5), BAUJAHR number(20,0), RADIUS number(20,5), KB_WERT_GMS number(20,5), KB_WERT_PC number(20,5), GEFAELLE number(20,5), GEFAELLE_HERKUNFT varchar2(5), STRANG_GEFAELLE number(20,5), HALTUNGSFLAECHE number(20,5), WARTUNGSINTERVALL_J number(20,5), WARTUNGSINTERVALL_M number(20,5), LETZTE_WARTUNG date,
      RATTENBEFALL number(20,0), RATTENBEKAEMPFUNG date, ANSCHAFFUNGSWERT number(20,5), NUTZUNGSDAUER number(20,5), EINSTAUHAEUFIGKEIT number(20,5), LETZTER_EINSTAU date, WASSERRECHTE varchar2(30), FLIESS_PFEIL varchar2(40), FLIESS_PFEIL_WINKEL number(20,5), EINLAUF_TIEFE number(20,5), AUSLAUF_TIEFE number(20,5), BEZEICHNUNG1 varchar2(40), BEZEICHNUNG2 varchar2(40), BEZEICHNUNG3 varchar2(40), STRANGLAENGE_HOR number(20,5), ABSTURZ_HOEHE number(20,5), SOHLSPRUNG_HOEHE number(20,5), MITTLERE_TIEFE number(20,5), EINLAUF_TEXT varchar2(5), AUSLAUF_TEXT varchar2(5), GEP_ANSCHRIEB number(10,0), PROFIL_BREITE_ALT number(10,5), GEFAELLE_ALT number(10,5), DIST_VS_E number(20,8), DIST_BS_A number(20,8), ID_STRASSE number(10,0), ID_PROFILART number(10,0), ID_STATUS number(10,0), ID_NUTZUNGS_ART number(10,0), ID_PROFILEINBAUTEN number(10,0),
      ID_VERBINDUNGSART number(10,0), ID_VERLEGEART number(10,0), ID_MATERIAL number(10,0), ID_BESCHICHTUNG_INNEN number(10,0), ID_BESCHICHTUNG_AUSSEN number(10,0), ID_EIGENTUMSVERHAELTNIS number(10,0), ID_BEWERT_FAKTOR_Q number(10,0), ID_FINANZIERUNGSKENNZIFFER number(10,0), ID_ABWASSER_ART number(10,0), ID_LAGE number(10,0), ID_WASSERSCHUTZZONE number(10,0), ID_BODENART number(10,0), ID_BETTUNG number(10,0), ID_GRUNDWASSERABSTAND number(10,0), ID_FUNKTION_HIERARCH number(10,0), ID_FUNKTION_HYDRAU number(10,0), ID_HOEHENGENAUIGKEIT number(10,0), ID_DICHTUNGSART number(10,0), ID_BEGR_BESCHICHTUNG number(10,0), ID_LAGEGENAUIGKEIT number(10,0), FID_KANAL number(10,0), FID_LAGEBEZEICHNUNG number(10,0), FID_VS number(10,0), FID_BS number(10,0), FID_EZG number(10,0), FID_EINRICHTUNGS_TYP number(10,0), KANALSYSTEM varchar2(1), RESTBUCHWERT number(10,2), RESTNUTZUNGSDAUER number(10,2), ABSCHREIB_ANTEIL number(10,4),
      CANALISATION_ANCIENID varchar2(100), CANALISATION_ANCIENCOLLAVAL varchar2(50), CANALISATION_ANCIENPTAVAL varchar2(50), CANALISATION_ANCIENCOLLAMONT varchar2(50), CANALISATION_ANCIENPTAMONT varchar2(50), ID_COMMUNE number(10,0), CANALISATION_PLAN varchar2(20), ID_POSITIONAVAL number(10,0), ID_POSITIONAMONT number(10,0), DATE_REHABIL date, NUMERO varchar2(10), ANNÉE_RÉHABIL number(4,0), COMMUNE number(10,0)
    -> AttributeFilter
AttributeFilter
    ATTR_NAME = DELETED
    ATTR_VALUES = <EMPTY>,<MISSING>,<NULL>,<UNFILTERED>,0,1
    0 -> oracle_geom_liner [input 1]
Note: collecteur geom
SIGE_ASSAINISSEMENT.AW_HALTUNG_GEO (reader ORACLE_NONSPATIAL_1)
    attributes: ID number(10,0), GID number(10,0), ESEQ number(10,0), SEQ number(10,0), ETYPE number(4,0), DA number(10,0), X1 number(20,8), Y1 number(20,8), Z1 number(20,8), CREATION_CODE_XY_1 number(4,0), ORIENTATION number(20,8), AZIMUTH number(20,8), ACCURACY_LEVEL number(20,8), M_DIRECTION number(20,8), M_DISTANCE number(20,8), CALC_CODE number(4,0), CALC_NUMBER number(10,0), AVG_DEV_XY number(20,8), AVG_DEV_Z number(20,8), CREATION_CODE_Z number(4,0), QUALITY number(10,0), SOURCE number(10,0), DELETED number(1,0), X2 number(20,8), Y2 number(20,8), Z2 number(20,8), CREATION_CODE_XY_2 number(4,0), X3 number(20,8), Y3 number(20,8), Z3 number(20,8),
      CREATION_CODE_XY_3 number(4,0), X4 number(20,8), Y4 number(20,8), Z4 number(20,8), CREATION_CODE_XY_4 number(4,0), X5 number(20,8), Y5 number(20,8), Z5 number(20,8), CREATION_CODE_XY_5 number(4,0), SEQ_ETYPE number(4,0), SEQ_PARAM1 number(20,8), SEQ_PARAM2 number(20,8), ORIGIN number(4,0), CLIPPING number(1,0), FID number(10,0), INVISIBLE number(1,0), DIM_X number(20,8), DIM_Y number(20,8), MUTATION_ID_CREATED number(10,0), MUTATION_STATUS_CREATED number(10,0), USER_CREATED varchar2(255), DATE_CREATED date, MUTATION_ID_DELETED number(10,0), MUTATION_STATUS_DELETED number(10,0), USER_DELETED varchar2(255), DATE_DELETED date, MUTATION_ID_MODIFIED number(10,0), USER_MODIFIED varchar2(255), DATE_MODIFIED date, GEO_CONSTRAINT number(1,0),
      AREA number(20,8), TD_POINT_NUMBER number(10,0), TD_LAYER number(10,0), TD_GROUP number(10,0), TD_NUMBER varchar2(50), PERIMETER number(20,8), LABEL_FROM number(10,0), LABEL_TO number(10,0), LABEL_TEXT varchar2(2000), LINEATTRIBUTE_ID number(10,0), SPATIAL_INDEX_100 number(12,0), SPATIAL_INDEX_200 number(12,0), SPATIAL_INDEX_400 number(12,0), TD_DA number(10,0), DTEXT number(1,0), FRAME number(1,0), FIELD_CODE number(4,0), SEQ_PARAM1_2 number(20,8), SEQ_PARAM2_2 number(20,8), SEQ_PARAM1_3 number(20,8), SEQ_PARAM2_3 number(20,8), SEQ_PARAM1_4 number(20,8), SEQ_PARAM2_4 number(20,8), SEQ_PARAM1_5 number(20,8), SEQ_PARAM2_5 number(20,8), SPATIAL_INDEX_25 number(12,0), SPATIAL_INDEX_50 number(12,0), Z_DIFF number(20,8), SEQ_PARAM3 number(20,8), SEQ_PARAM3_2 number(20,8),
      SEQ_PARAM3_3 number(20,8), SEQ_PARAM3_4 number(20,8), SEQ_PARAM3_5 number(20,8), Z_TERRAIN number(20,8), TB_POINT_NUMBER number(15,0)
    -> oracle_geom_liner [input 2]
oracle_geom_liner
    Z1 = @Value(Z1)
    GID = @Value(GID)
    Y1 = @Value(Y1)
    X1 = @Value(X1)
    FeatureMerger_Merged -> AttributeRenamer
AttributeRenamer
    ATTR_LIST = STRANGLAENGE,effective_length,,PROFIL_HOEHE,clear_height,,BAUJAHR,year_of_construction,,DATE_REHABIL,year_of_replacement,,NAME,identifier,,BEMERKUNG,remark,
    -> AttributeCopier
Note: copier la distance, altitude
AttributeCopier
    ATTR_LIST = effective_length,pipe_length,,firstpoint_z,rp_from_level,,lastpoint_z,rp_to_level,
    -> AttributeValueMapper
Note: Profil
AttributeValueMapper
    LUT = 1,ch11h8mwPP000018,3,rectangle,2,ch11h8mwPP000013,5,ch11h8mwPP000017,6,ovoide,7,ch11h8mwPP000016
    DEFAULT_VALUE = ch11h8mwPP000017
    SRC = ID_PROFILART
    VAL_ATTR = fk_pipe_profile
    DIRECTION = Forward (Source To Destination)
    -> StringLengthFormatter
Note: remark TBC
StringLengthFormatter
    Input_Attr = @Value(remark)
    RESULT_Attr = remark
    StringLength = 80
    -> AttributeFilter_3
Note: hauteur null
AttributeFilter_3
    ATTR_NAME = clear_height
    ATTR_VALUES = <EMPTY>,<MISSING>,<NULL>,<UNFILTERED>
    <EMPTY> -> AttributeFilter_2
    <NULL> -> AttributeCopier_2
    <UNFILTERED> -> AttributeFilter_2
Note: largeur => hauteur
AttributeCopier_2
    ATTR_LIST = PROFIL_BREITE,clear_height,
    -> AttributeFilter_2
AttributeFilter_2
    ATTR_NAME = fk_pipe_profile
    ATTR_VALUES = <EMPTY>,<MISSING>,<NULL>,<UNFILTERED>,ovoide,rectangle
    ovoide -> TestFilter
    rectangle -> TestFilter_2
    <UNFILTERED> -> AttributeValueMapper_2
TestFilter_2
    DEFAULT_VALUE = <UNFILTERED>
    TEST_LIST = BOOL_OP,AND,COMPOSITE_TEST,<Unused>,TEST_CLAUSE,"TEST Evaluate(@abs(@Value(clear_height)/@Value(PROFIL_BREITE)-1.0)) < 0.009",carre,BOOL_OP,AND,COMPOSITE_TEST,<Unused>,TEST_CLAUSE,"TEST Evaluate(@abs(@Value(clear_height)/@Value(PROFIL_BREITE)-.67)) < .009",rect .67 2/3,BOOL_OP,AND,COMPOSITE_TEST,<Unused>,TEST_CLAUSE,"TEST @Evaluate(Evaluate(@abs(@Value(clear_height)/@Value(PROFIL_BREITE)-1.5))) < .009",rect. 1.5,BOOL_OP,AND,COMPOSITE_TEST,<Unused>,TEST_CLAUSE,"TEST @Evaluate(Evaluate(@abs(@Value(clear_height)/@Value(PROFIL_BREITE)-1.42))) <= .009",rect 850/600
    carre -> AttributeCreator_4
    rect 850/600 -> AttributeCreator_7
    rect. 1.5 -> AttributeCreator_6
    rect .67 2/3 -> AttributeCreator_5
    <UNFILTERED> -> AttributeValueMapper_2
AttributeCreator_4
    ATTR_LIST = fk_pipe_profile,ch11h8mwPP000023
    -> AttributeValueMapper_2
AttributeCreator_5
    ATTR_LIST = fk_pipe_profile,ch11h8mwPP000024
    -> AttributeValueMapper_2
AttributeCreator_6
    ATTR_LIST = fk_pipe_profile,ch11h8mwPP000025
    -> AttributeValueMapper_2
AttributeCreator_7
    ATTR_LIST = fk_pipe_profile,ch11h8mwPP000026
    -> AttributeValueMapper_2
TestFilter
    DEFAULT_VALUE = <UNFILTERED>
    TEST_LIST = BOOL_OP,AND,COMPOSITE_TEST,<Unused>,TEST_CLAUSE,"TEST Evaluate(@abs(@Value(clear_height)/@Value(PROFIL_BREITE)-1.5)) < 0.009",ovoide 1.5,BOOL_OP,AND,COMPOSITE_TEST,<Unused>,TEST_CLAUSE,"TEST Evaluate(@abs(@Value(clear_height)/@Value(PROFIL_BREITE)-.75)) < .009",ovoide .75,BOOL_OP,AND,COMPOSITE_TEST,<Unused>,TEST_CLAUSE,"TEST @Evaluate(Evaluate(@abs(@Value(clear_height)/@Value(PROFIL_BREITE)-1.2))) < .009",ovoide 1.2
    <UNFILTERED> -> AttributeValueMapper_2
    ovoide 1.5 -> AttributeCreator
    ovoide 1.2 -> AttributeCreator_2
    ovoide .75 -> AttributeCreator_3
AttributeCreator
    ATTR_LIST = fk_pipe_profile,ch11h8mwPP000021
    -> AttributeValueMapper_2
AttributeCreator_3
    ATTR_LIST = fk_pipe_profile,ch11h8mwPP000020
    -> AttributeValueMapper_2
AttributeCreator_2
    ATTR_LIST = fk_pipe_profile,ch11h8mwPP000022
    -> AttributeValueMapper_2
Note: fct hierarchique
AttributeValueMapper_2
    LUT = 11,5066,3,5069,4,5063,10,5066,9,5074,1,5063
    SRC = ID_FUNKTION_HIERARCH
    VAL_ATTR = function_hierarchic
    DIRECTION = Forward (Source To Destination)
    -> AttributeValueMapper_3
Note: fct hydraulique
AttributeValueMapper_3
    LUT = 2,367,5,23,10,5321
    SRC = ID_FUNKTION_HYDRAU
    VAL_ATTR = function_hydraulic
    DIRECTION = Forward (Source To Destination)
    -> AttributeValueMapper_4
Note: utilisation
AttributeValueMapper_4
    LUT = 5,4514,1,4524,6,4526,4,4522,7,4571,11,4571,10,5322,12,5322
    DEFAULT_VALUE = 6326
    SRC = ID_NUTZUNGS_ART
    VAL_ATTR = usage_current
    DIRECTION = Forward (Source To Destination)
    -> AttributeValueMapper_5
Note: materiau
AttributeValueMapper_5
    LUT = 10005,2754,3,3638,10007,3638,5,3638,25,5081,10004,148,10,148,15,5078,38,3016,10009,3016,10000,5079,1,2762,10008,5080,33,153
    DEFAULT_VALUE = 5381
    SRC = ID_MATERIAL
    VAL_ATTR = material
    DIRECTION = Forward (Source To Destination)
    -> AttributeValueMapper_6
Note: precision plan
AttributeValueMapper_6
    LUT = 1,5380,2,5378,3,5380,4,5378
    DEFAULT_VALUE = 5379
    SRC = ID_LAGEGENAUIGKEIT
    VAL_ATTR = horizontal_positioning
    DIRECTION = Forward (Source To Destination)
    -> AttributeRemover
    -> Inspector
AttributeRemover
    REMOVE_ATTRS = ABSCHREIB_ANTEIL,ABSTURZ,ABSTURZ_HOEHE,ANNÉE_RÉHABIL,ANSCHAFFUNGSWERT,AREA_NOMINAL,AUSLAUF_TEXT,AUSLAUF_TIEFE,BEMERKUNG,BEZEICHNUNG1,BEZEICHNUNG2,BEZEICHNUNG3,CANALISATION_ANCIENCOLLAMONT,CANALISATION_ANCIENCOLLAVAL,CANALISATION_ANCIENID,CANALISATION_ANCIENPTAMONT,CANALISATION_ANCIENPTAVAL,CANALISATION_PLAN,COMMUNE,DATEI,DELETED,DIST_BS_A,DIST_VS_E,EINLAUF_TEXT,EINLAUF_TIEFE,EINSTAUHAEUFIGKEIT,F1,F2,F3,FID,FID_BS,FID_EINRICHTUNGS_TYP,FID_EZG,FID_KANAL,FID_LAGEBEZEICHNUNG,FID_VS,firstpoint_x,firstpoint_y,firstpoint_z,FLIESS_PFEIL,FLIESS_PFEIL_WINKEL,GEFAELLE,GEFAELLE_ALT,GEFAELLE_HERKUNFT,GEP_ANSCHRIEB,GID,HALTUNGSFLAECHE,HALTUNGSLAENGE,ID_ABWASSER_ART,ID_BEGR_BESCHICHTUNG,ID_BESCHICHTUNG_AUSSEN,ID_BESCHICHTUNG_INNEN,ID_BETTUNG,ID_BEWERT_FAKTOR_Q,ID_BODENART,ID_COMMUNE,ID_DICHTUNGSART,ID_EIGENTUMSVERHAELTNIS,ID_FINANZIERUNGSKENNZIFFER,ID_FUNKTION_HIERARCH,ID_FUNKTION_HYDRAU,ID_GRUNDWASSERABSTAND,ID_HOEHENGENAUIGKEIT,ID_LAGE,ID_LAGEGENAUIGKEIT,ID_MATERIAL,ID_NUTZUNGS_ART,ID_POSITIONAMONT,ID_POSITIONAVAL,ID_PROFILART,ID_PROFILEINBAUTEN,ID_STATUS,ID_STRASSE,ID_VERBINDUNGSART,ID_VERLEGEART,ID_WASSERSCHUTZZONE,KANALSYSTEM,KB_WERT_GMS,KB_WERT_PC,LAENGEN_HERKUNFT,lastpoint_x,lastpoint_y,lastpoint_z,LETZTE_WARTUNG,LETZTER_EINSTAU,linestring,MITTLERE_TIEFE,NAME,NAME2,NUMERO,NUTZUNGSDAUER,PROFIL_BREITE_ALT,PROFIL_HOEHE,RADIUS,RATTENBEFALL,RATTENBEKAEMPFUNG,RESTBUCHWERT,RESTNUTZUNGSDAUER,ROHRLAENGE,SOHLSPRUNG,SOHLSPRUNG_HOEHE,STRANG_GEFAELLE,STRANGLAENGE_HOR,WARTUNGSINTERVALL_J,WARTUNGSINTERVALL_M,WASSERRECHTE,X1,Y1,list{0}.ACCURACY_LEVEL,list{0}.AREA,list{0}.AVG_DEV_XY,list{0}.AVG_DEV_Z,list{0}.AZIMUTH,list{0}.CALC_CODE,list{0}.CALC_NUMBER,list{0}.CLIPPING,list{0}.CREATION_CODE_XY_1,list{0}.CREATION_CODE_XY_2,list{0}.CREATION_CODE_XY_3,list{0}.CREATION_CODE_XY_4,list{0}.CREATION_CODE_XY_5,list{0}.CREATION_CODE_Z,list{0}.DA,list{0}.DATE_CREATED,list{0}.DATE_DELETED,list{0}.DATE_MODIFIED,list{0}.DELETED,list{0}.DIM_X,list{0}.DIM_Y,list{0}.DTEXT,list{0}.ESEQ,list{0}.ETYPE,list{0}.FID,list{0}.FIELD_CODE,list{0}.FRAME,list{0}.GEO_CONSTRAINT,list{0}.GID,list{0}.ID,list{0}.INVISIBLE,list{0}.LABEL_FROM,list{0}.LABEL_TEXT,list{0}.LABEL_TO,list{0}.LINEATTRIBUTE_ID,list{0}.M_DIRECTION,list{0}.M_DISTANCE,list{0}.MUTATION_ID_CREATED,list{0}.MUTATION_ID_DELETED,list{0}.MUTATION_ID_MODIFIED,list{0}.MUTATION_STATUS_CREATED,list{0}.MUTATION_STATUS_DELETED,list{0}.ORIENTATION,list{0}.ORIGIN,list{0}.PERIMETER,list{0}.QUALITY,list{0}.SEQ,list{0}.SEQ_ETYPE,list{0}.SEQ_PARAM1,list{0}.SEQ_PARAM1_2,list{0}.SEQ_PARAM1_3,list{0}.SEQ_PARAM1_4,list{0}.SEQ_PARAM1_5,list{0}.SEQ_PARAM2,list{0}.SEQ_PARAM2_2,list{0}.SEQ_PARAM2_3,list{0}.SEQ_PARAM2_4,list{0}.SEQ_PARAM2_5,list{0}.SEQ_PARAM3,list{0}.SEQ_PARAM3_2,list{0}.SEQ_PARAM3_3,list{0}.SEQ_PARAM3_4,list{0}.SEQ_PARAM3_5,list{0}.SOURCE,list{0}.SPATIAL_INDEX_25,list{0}.SPATIAL_INDEX_50,list{0}.SPATIAL_INDEX_100,list{0}.SPATIAL_INDEX_200,list{0}.SPATIAL_INDEX_400,list{0}.TB_POINT_NUMBER,list{0}.TD_DA,list{0}.TD_GROUP,list{0}.TD_LAYER,list{0}.TD_NUMBER,list{0}.TD_POINT_NUMBER,list{0}.USER_CREATED,list{0}.USER_DELETED,list{0}.USER_MODIFIED,list{0}.X2,list{0}.X3,list{0}.X4,list{0}.X5,list{0}.xy,list{0}.Y2,list{0}.Y3,list{0}.Y4,list{0}.Y5,list{0}.Z_DIFF,list{0}.Z_TERRAIN,list{0}.Z1,list{0}.Z2,list{0}.Z3,list{0}.Z4,list{0}.Z5
    -> qgep.vw_wizard_reach_channel (writer POSTGRES_2)
qgep.vw_wizard_reach_channel (writer POSTGRES_2)
    attributes: clear_height char(200), effective_length char(200), pipe_length char(200), year_of_construction char(200), year_of_replacement char(200), progression_geometry char(200), rp_from_level char(200), rp_to_level char(200), fk_pipe_profile char(200), function_hierarchic char(200), function_hydraulic char(200), usage_current char(200), material char(200), identifier char(200), remark char(200)
Inspector

FME custom transformer oracle_geom_liner

Parameters:
- Y1 = @Value(Y1)
- X1 = @Value(X1)
- GID = @Value(GID)
- Z1 = @Value(Z1)

AttributeRemover_2_Input (input)
    -> Sorter
Note: Tri par GID puis par SEQ
Sorter
    SORT_PARM = GID NUMERIC ASCENDING SEQ NUMERIC ASCENDING
    SORTED -> StringFormatter
Note: Transforme les coordonnées en texte
StringFormatter
    SRC_ATTRS = X1,Y1,Z1
    FORMAT = .10f
    -> StringConcatenator_2
Note: Concatene X et Y dans xy
StringConcatenator_2
    PARM_LINE = @Value(Y1) @Value(X1) @Value(Z1)
    VAL_ATTR = xy
    -> AttributeRemover_3
Note: Suppression X et Y
AttributeRemover_3
    REMOVE_ATTRS = X1,Y1,Z1
    -> ListBuilder
Note: Grouper les éléments par GID (triés en SEQ)
ListBuilder
    GRP_BY = GID
    LIST_NAME = list
    -> ListConcatenator
Note: Concatene les xy des memes conduites
ListConcatenator
    SEP = ", "
    VAL_ATTR = _linestring
    LIST_ATTR = list{}.xy
    DROP_EMPTY_PARTS = No
    -> StringConcatenator_3
Note: Concatene avec les parenthèses
StringConcatenator_3
    PARM_LINE = LINESTRING(@Value(_linestring))
    VAL_ATTR = linestring
    -> AttributeRemover_4
Note: Suppression des champs intermediaires
AttributeRemover_4
    REMOVE_ATTRS = _linestring,list{0}.GID,list{0}.xy
    -> GeometryReplacer
Note: Create GEOM from WKT
GeometryReplacer
    KIND_LONG = OGC Well Known Text
    SRS_AXIS_ORDER_DISPLAY = Automatic
    ATTR = linestring
    -> GeometryOGCValidator
GeometryOGCValidator
    VALIDATION_TYPE = Valid
    PASSED -> CoordinateSystemSetter
Note: Write WKB from GEOM
CoordinateSystemSetter
    COORDSYS = EPSG:21781
    -> GeometryExtractor
GeometryExtractor
    KIND_LONG = OGC Well Known Text
    OGCVERSION = 1.1
    ATTR = progression_geometry
    -> StringConcatenator
StringConcatenator
    PARM_LINE = SRID=21781;@Value(progression_geometry)
    VAL_ATTR = progression_geometry
    ACTION = Create New Attribute
    -> CoordinateExtractor
Note: first point
CoordinateExtractor
    Z_DEFAULT = -9999
    Z_ATTR = firstpoint_z
    Y_ATTR = firstpoint_y
    IND = 0
    X_ATTR = firstpoint_x
    -> CoordinateExtractor_2
Note: last point
CoordinateExtractor_2
    Z_DEFAULT = -9999
    Z_ATTR = lastpoint_z
    Y_ATTR = lastpoint_y
    IND = -1
    X_ATTR = lastpoint_x
    -> FeatureMerger [input 2]
FeatureMerger_Requestor (input)
    -> FeatureMerger [input 1]
FeatureMerger
    JOIN_KEYS = @Value(GID) @Value(GID) AUTO
    MERGE_TYPE = Attributes and Geometry
    ATTR_CONFLICT_RES = Use Requestor
    PROCESS_DUPS = No
    SUPPLIERS_FIRST = No
    ATTR_ACCUM_MODE = Merge Supplier
    MERGED -> FeatureMerger_Merged (output)
FeatureMerger_Merged (output)

FME custom transformer StringLengthFormatter
Formats attributes to the specified length either truncating or padding the incoming attributes. 
For example, if you set the String Length parameter to 5:
- If an input attribute value consists of only 3 characters, this transformer will add two spaces to the end of the attribute value.
- If an input attribute value has a length of 7, this transformer will remove two characters from the end of it.
User has to connect this transformer in a workspace and choose a source attribute, a destination attribute and a desired string length.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- StringLength = 5   # String length
- Input_Attr =   # Source Attribute
- RESULT_Attr =   # Destination Attribute

INPUT (input)
    -> ParameterFetcher
Note: Retrieve parameters
ParameterFetcher
    ATTR_LIST = _slfLength {$(StringLength)} _slfSource {$(Input_Attr)}
    -> STRINGLENGTHCALCULATOR
Note: Determine the input string's length
STRINGLENGTHCALCULATOR: StringLengthCalculator
    LENGTH_ATTR = _slfSourceLength
    SRC_ATTR = _slfSource
    -> TESTER
Note: Created by Dmitri Bagh / November 11, 2005
Note: Check whether input / string is longer than / user's chosen length
TESTER: Tester
    TEST_CLAUSE = TEST "@Value(_slfSourceLength)" > "@Value(_slfLength)"
    TEST_MODE = Automatic
    BOOL_OP = OR
    TEST_DESCRIPTION = ""
    TEST_LIST = &_slfSourceLength,>,&_slfLength
    FAILED -> STRINGPADDER
    PASSED -> ExpressionEvaluator
Note: If it is shorter or equal, run it / through the StringPadder
STRINGPADDER: StringPadder
    RESULT = $(RESULT_Attr)
    SRC = _slfSource
    SIDE = Right
    WIDTH = @Value(_slfLength)
    -> ATTRIBUTEREMOVER
Note: Clean up
ATTRIBUTEREMOVER: AttributeRemover
    REMOVE_ATTRS = _slfLength,_slfSource,_slfSourceLength
    -> OUTPUT (output)
OUTPUT (output)

Bookmark: If it is longer, remove the extra characters
ExpressionEvaluator
    EXPRESSION = @Value(_slfLength)-1
    VAL_ATTR = _slfLength
    -> SUBSTRINGEXTRACTOR
SUBSTRINGEXTRACTOR: SubstringExtractor
    RESULT_ATTR = $(RESULT_Attr)
    END = @Value(_slfLength)
    START = 0
    SRC_ATTR = _slfSource
    -> ATTRIBUTEREMOVER
