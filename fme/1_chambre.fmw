FME workspace 1_chambre.fmw

Parameters:
- SourceDataset_ORACLE_NONSPATIAL = SYSTEM@orcl   # Connection
- SourceDataset_POSTGRES = sige@172.24.171.203:5432/qgep   # Connection
- DestDataset_POSTGRES = sige@172.24.171.203:5432/qgep   # Connection
- SourceDataset_ORACLE_NONSPATIAL_5 = SYSTEM@orcl   # Connection
- SourceDataset_ORACLE_NONSPATIAL_7 = SYSTEM@orcl   # Connection
- DestDataset_POSTGRES_4 = sige@172.24.171.203:5432/qgep   # Connection

Readers:
- ORACLE_NONSPATIAL_1: ORACLE_NONSPATIAL from $(SourceDataset_ORACLE_NONSPATIAL)
- POSTGRES_1: POSTGRES from $(SourceDataset_POSTGRES)
- ORACLE_NONSPATIAL_2: ORACLE_NONSPATIAL from $(SourceDataset_ORACLE_NONSPATIAL_5)
- ORACLE_NONSPATIAL_3: ORACLE_NONSPATIAL from $(SourceDataset_ORACLE_NONSPATIAL_7)

Writers:
- POSTGRES_2: POSTGRES to $(DestDataset_POSTGRES)
- POSTGRES_3: POSTGRES to $(DestDataset_POSTGRES_4)

Note: chambre
SIGE_ASSAINISSEMENT.AW_SCHACHT (reader ORACLE_NONSPATIAL_1)
    attributes: FID number(10,0), GID number(10,0), DELETED number(1,0), AREA_NOMINAL number(20,8), POINT_NUMBER varchar2(50), NAME varchar2(60), SONDERBAUWERK varchar2(20), SBW number(20,0), NAME2 varchar2(20), BEMERKUNG varchar2(255), F1 varchar2(20), F2 varchar2(20), F3 varchar2(20), TIEFE number(20,5), BAUJAHR number(20,0), DN number(20,5), BREITE number(20,5), UNTEN_DN number(20,5), UNTEN_BREITE number(20,5), WANDDICKE number(20,5), SCHACHTHALS varchar2(5), ANSCHLUESSE number(20,5), UEBERGANGSPLATTE varchar2(5), ABDECKPLATTE varchar2(5), BAUGRUBENBREITE number(20,5), BOESCHUNGSWINKEL number(20,5), FLAECHE number(20,5), UEBERSTAUHAEUFIGKEIT number(20,5), LETZTER_UEBERSTAU date, BEZEICHNUNG1 varchar2(20),
      BEZEICHNUNG2 varchar2(20), SKALIERFAKTOR number(20,5), ORTSBEZEICHNUNG varchar2(50), UNTEN_HOEHE number(20,5), ANZAHL_EINLAEUFE number(2,0), ANZAHL_AUSLAEUFE number(2,0), TB_POINT_NUMBER number(15,0), KOMPLEX_LABEL varchar2(2000), ID_STATUS number(10,0), ID_STRASSE number(10,0), ID_LAGE number(10,0), ID_SCHACHTART number(10,0), ID_ZUGAENGLICHKEIT number(10,0), ID_FUNKTION number(10,0), ID_MATERIAL number(10,0), ID_FINANZIERUNGSKENNZIFFER number(10,0), ID_HOEHENGENAUIGKEIT number(10,0), ID_LAGEGENAUIGKEIT number(10,0), ID_KONUS_BAUSTOFF number(10,0), ID_OBEN_BAUSTOFF number(10,0), ID_EINSTIEGHILFE number(10,0), ID_UNTEN_BAUSTOFF number(10,0), ID_GERINNE_BAUSTOFF number(10,0), ID_GRUENDUNG number(10,0), ID_SCHACHT_FORM number(10,0), ID_UNTEN_FORM number(10,0), ID_BEGR_BESCHICHTUNG number(10,0), ID_STEIGEISENGAENGE number(10,0), ID_VERKEHRSFLAECHE number(10,0), ID_GERINNE_FORM number(10,0),
      ID_NUTZUNGS_ART number(10,0), ID_BESCHICHTUNG_INNEN number(10,0), ID_BESCHICHTUNG_AUSSEN number(10,0), ID_EIGENTUMSVERHAELTNIS number(10,0), ID_BAUGRUBENFORM number(10,0), FID_KS number(10,0), FID_LAGEBEZEICHNUNG number(10,0), FID_EINRICHTUNGS_TYP number(10,0), CHAMBRE_ANCIENID varchar2(20), FID_COLLECTEUR number(10,0), ID_COMMUNE number(10,0), CHAMBRE_PLAN varchar2(20), ID_BRISECHARGE number(10,0), ID_COUPEVENT number(10,0), ID_LIMITEURDEBIT number(10,0), ID_PROFIL number(10,0), CHAMBRE_CONTROLE date, CHAMBRE_NUMEROECA varchar2(50), CHAMBRE_PARCELLE varchar2(20), CHAMBRE_CLASSE varchar2(50), CHAMBRE_TYPE varchar2(50), ID_AERATION number(10,0), DATE_REHABIL date, ID_PROFIL_CHAMBRE number(10,0), LONGUEUR number(20,5), COMMUNE number(10,0)
    -> AttributeFilter
AttributeFilter
    ATTR_VALUES = <EMPTY>,<MISSING>,<NULL>,<UNFILTERED>,0,1
    ATTR_NAME = DELETED
    0 -> oracle_geom_point [input 1]
    0 -> AttributeFilter_3
Note: accès
AttributeFilter_3
    ATTR_VALUES = <EMPTY>,<MISSING>,<NULL>,<UNFILTERED>
    ATTR_NAME = ID_EINSTIEGHILFE
    <UNFILTERED> -> AttributeValueMapper_4
AttributeValueMapper_4
    DIRECTION = Forward (Source To Destination)
    LUT = 1,240,2,91,3,92,4,241,5,3473,6,3048
    SRC = ID_EINSTIEGHILFE
    VAL_ATTR = kind
    -> AttributeRenamer_4
AttributeRenamer_4
    ATTR_LIST = FID,identifier,fdsfs
    -> qgep.vw_access_aid (writer POSTGRES_3)
qgep.vw_access_aid (writer POSTGRES_3)
    attributes: kind char(200), identifier char(200)
Note: chambre geom
SIGE_ASSAINISSEMENT.AW_SCHACHT_GEO (reader ORACLE_NONSPATIAL_1)
    attributes: ID number(10,0), GID number(10,0), ESEQ number(10,0), SEQ number(10,0), ETYPE number(4,0), DA number(10,0), X1 number(20,8), Y1 number(20,8), Z1 number(20,8), CREATION_CODE_XY_1 number(4,0), ORIENTATION number(20,8), AZIMUTH number(20,8), ACCURACY_LEVEL number(20,8), M_DIRECTION number(20,8), M_DISTANCE number(20,8), CALC_CODE number(4,0), CALC_NUMBER number(10,0), AVG_DEV_XY number(20,8), AVG_DEV_Z number(20,8), CREATION_CODE_Z number(4,0), QUALITY number(10,0), SOURCE number(10,0), DELETED number(1,0), X2 number(20,8), Y2 number(20,8), Z2 number(20,8), CREATION_CODE_XY_2 number(4,0), X3 number(20,8), Y3 number(20,8), Z3 number(20,8),
      CREATION_CODE_XY_3 number(4,0), X4 number(20,8), Y4 number(20,8), Z4 number(20,8), CREATION_CODE_XY_4 number(4,0), X5 number(20,8), Y5 number(20,8), Z5 number(20,8), CREATION_CODE_XY_5 number(4,0), SEQ_ETYPE number(4,0), SEQ_PARAM1 number(20,8), SEQ_PARAM2 number(20,8), ORIGIN number(4,0), CLIPPING number(1,0), FID number(10,0), INVISIBLE number(1,0), DIM_X number(20,8), DIM_Y number(20,8), MUTATION_ID_CREATED number(10,0), MUTATION_STATUS_CREATED number(10,0), USER_CREATED varchar2(255), DATE_CREATED date, MUTATION_ID_DELETED number(10,0), MUTATION_STATUS_DELETED number(10,0), USER_DELETED varchar2(255), DATE_DELETED date, MUTATION_ID_MODIFIED number(10,0), USER_MODIFIED varchar2(255), DATE_MODIFIED date, GEO_CONSTRAINT number(1,0),
      AREA number(20,8), TD_POINT_NUMBER number(10,0), TD_LAYER number(10,0), TD_GROUP number(10,0), TD_NUMBER varchar2(50), PERIMETER number(20,8), LABEL_FROM number(10,0), LABEL_TO number(10,0), LABEL_TEXT varchar2(2000), LINEATTRIBUTE_ID number(10,0), SPATIAL_INDEX_100 number(12,0), SPATIAL_INDEX_200 number(12,0), SPATIAL_INDEX_400 number(12,0), TD_DA number(10,0), DTEXT number(1,0), FRAME number(1,0), FIELD_CODE number(4,0), SEQ_PARAM1_2 number(20,8), SEQ_PARAM2_2 number(20,8), SEQ_PARAM1_3 number(20,8), SEQ_PARAM2_3 number(20,8), SEQ_PARAM1_4 number(20,8), SEQ_PARAM2_4 number(20,8), SEQ_PARAM1_5 number(20,8), SEQ_PARAM2_5 number(20,8), SPATIAL_INDEX_25 number(12,0), SPATIAL_INDEX_50 number(12,0), Z_DIFF number(20,8), SEQ_PARAM3 number(20,8), SEQ_PARAM3_2 number(20,8),
      SEQ_PARAM3_3 number(20,8), SEQ_PARAM3_4 number(20,8), SEQ_PARAM3_5 number(20,8), Z_TERRAIN number(20,8), TB_POINT_NUMBER number(15,0)
    -> oracle_geom_point [input 2]
oracle_geom_point
    Y1 = @Value(Y1)
    X1 = @Value(X1)
    GID = @Value(GID)
    FeatureMerger_2_Complete -> AttributeRenamer
AttributeRenamer
    ATTR_LIST = NAME2,identifier,,BAUJAHR,year_of_construction,,TIEFE,depth,,DN,dimension1,,BREITE,dimension2,,UNTEN_HOEHE,bottom_level,,DATE_REHABIL,year_of_replacement,,ORTSBEZEICHNUNG,location_name,,BEMERKUNG,remark,,geometry,node_geometry,,Z1,level,,FID,old_obj_id,
    -> AttributeCreator
Note: bottom_level
AttributeCreator
    ATTR_LIST = bottom_level,@sub(@Value(level),@Value(depth))
    -> AttributeFilter_2
Note: rapport propriété
AttributeFilter_2
    ATTR_VALUES = <EMPTY>,<MISSING>,<NULL>,<UNFILTERED>
    ATTR_NAME = ID_EIGENTUMSVERHAELTNIS
    <UNFILTERED> -> FeatureMerger [input 1]
    <NULL> -> AttributeValueMapper
    <EMPTY> -> AttributeValueMapper
Note: couvercle
SIGE_ASSAINISSEMENT.AW_SCHACHT_DECKEL (reader ORACLE_NONSPATIAL_2)
    attributes: FID number(10,0), GID number(10,0), DELETED number(1,0), AREA_NOMINAL number(20,8), POINT_NUMBER varchar2(50), NAME varchar2(60), DECKEL_DN number(20,5), DECKEL_BREITE number(20,5), NR number(20,0), BEZUGSDECKEL number(20,0), SKALIERFAKTOR number(20,5), SONDERBAUWERK_ID number(10,0), F1 varchar2(20), BEMERKUNG varchar2(255), BEZEICHNUNG1 varchar2(20), TB_POINT_NUMBER number(15,0), ID_DECKEL_FORM number(10,0), ID_HOEHENGENAUIGKEIT number(10,0), ID_BELASTUNG number(10,0), ID_MATERIAL number(10,0), ID_KENNUNG number(10,0), ID_LAGEGENAUIGKEIT number(10,0), FID_HERSTELLER number(10,0), FID_SCHACHT number(10,0), FID_SCHACHT2 number(10,0)
    -> oracle_geom_point_2 [input 1]
Note: couvercle geom
SIGE_ASSAINISSEMENT.AW_SCHACHT_DECKEL_GEO (reader ORACLE_NONSPATIAL_3)
    attributes: ID number(10,0), GID number(10,0), ESEQ number(10,0), SEQ number(10,0), ETYPE number(4,0), DA number(10,0), X1 number(20,8), Y1 number(20,8), Z1 number(20,8), CREATION_CODE_XY_1 number(4,0), ORIENTATION number(20,8), AZIMUTH number(20,8), ACCURACY_LEVEL number(20,8), M_DIRECTION number(20,8), M_DISTANCE number(20,8), CALC_CODE number(4,0), CALC_NUMBER number(10,0), AVG_DEV_XY number(20,8), AVG_DEV_Z number(20,8), CREATION_CODE_Z number(4,0), QUALITY number(10,0), SOURCE number(10,0), DELETED number(1,0), X2 number(20,8), Y2 number(20,8), Z2 number(20,8), CREATION_CODE_XY_2 number(4,0), X3 number(20,8), Y3 number(20,8), Z3 number(20,8),
      CREATION_CODE_XY_3 number(4,0), X4 number(20,8), Y4 number(20,8), Z4 number(20,8), CREATION_CODE_XY_4 number(4,0), X5 number(20,8), Y5 number(20,8), Z5 number(20,8), CREATION_CODE_XY_5 number(4,0), SEQ_ETYPE number(4,0), SEQ_PARAM1 number(20,8), SEQ_PARAM2 number(20,8), ORIGIN number(4,0), CLIPPING number(1,0), FID number(10,0), INVISIBLE number(1,0), DIM_X number(20,8), DIM_Y number(20,8), MUTATION_ID_CREATED number(10,0), MUTATION_STATUS_CREATED number(10,0), USER_CREATED varchar2(255), DATE_CREATED date, MUTATION_ID_DELETED number(10,0), MUTATION_STATUS_DELETED number(10,0), USER_DELETED varchar2(255), DATE_DELETED date, MUTATION_ID_MODIFIED number(10,0), USER_MODIFIED varchar2(255), DATE_MODIFIED date, GEO_CONSTRAINT number(1,0),
      AREA number(20,8), TD_POINT_NUMBER number(10,0), TD_LAYER number(10,0), TD_GROUP number(10,0), TD_NUMBER varchar2(50), PERIMETER number(20,8), LABEL_FROM number(10,0), LABEL_TO number(10,0), LABEL_TEXT varchar2(2000), LINEATTRIBUTE_ID number(10,0), SPATIAL_INDEX_100 number(12,0), SPATIAL_INDEX_200 number(12,0), SPATIAL_INDEX_400 number(12,0), TD_DA number(10,0), DTEXT number(1,0), FRAME number(1,0), FIELD_CODE number(4,0), SEQ_PARAM1_2 number(20,8), SEQ_PARAM2_2 number(20,8), SEQ_PARAM1_3 number(20,8), SEQ_PARAM2_3 number(20,8), SEQ_PARAM1_4 number(20,8), SEQ_PARAM2_4 number(20,8), SEQ_PARAM1_5 number(20,8), SEQ_PARAM2_5 number(20,8), SPATIAL_INDEX_25 number(12,0), SPATIAL_INDEX_50 number(12,0), Z_DIFF number(20,8), SEQ_PARAM3 number(20,8), SEQ_PARAM3_2 number(20,8),
      SEQ_PARAM3_3 number(20,8), SEQ_PARAM3_4 number(20,8), SEQ_PARAM3_5 number(20,8), Z_TERRAIN number(20,8), TB_POINT_NUMBER number(15,0)
    -> oracle_geom_point_2 [input 2]
oracle_geom_point_2
    Y1 = @Value(Y1)
    X1 = @Value(X1)
    GID = @Value(GID)
    FeatureMerger_2_Complete -> AttributeRenamer_3
AttributeRenamer_3
    ATTR_LIST = geometry,situation_geometry,
    -> FeatureMerger_3 [input 2]
Note: qgep organisation
qgep.od_organisation (reader POSTGRES_1)
    attributes: obj_id varchar(16),BTREE, identifier varchar(80),PRIKEY, remark varchar(80), uid varchar(12), last_modification timestamp, dataowner varchar(80), provider varchar(80), old_obj_id text
    -> AttributeRenamer_2
AttributeRenamer_2
    ATTR_LIST = obj_id,fk_owner,
    -> AttributeRemover_2
AttributeRemover_2
    REMOVE_ATTRS = uid,dataowner,identifier,last_modification,provider,remark
    -> FeatureMerger [input 2]
Note: provider
FeatureMerger
    MERGE_TYPE = Attributes Only
    JOIN_KEYS = @Value(ID_EIGENTUMSVERHAELTNIS) @Value(old_obj_id) AUTO
    SUPPLIERS_FIRST = No
    PROCESS_DUPS = No
    ATTR_ACCUM_MODE = Merge Supplier
    ATTR_CONFLICT_RES = Use Requestor
    MERGED -> AttributeValueMapper
Note: materiau TBC
AttributeValueMapper
    DIRECTION = Forward (Source To Destination)
    LUT = 2,4541,3,4541,4,4541,8,4540,10,4540,11,4540,17,4542,22,4543,10000,4542,10001,4540,FME_NULL_VALUE,4543
    SRC = ID_MATERIAL
    VAL_ATTR = material
    -> AttributeValueMapper_2
Note: type/fonction TBC
AttributeValueMapper_2
    DIRECTION = Forward (Source To Destination)
    LUT = 3,4532,14,204,26,5346,38,5345,24,4536,4,1008,10002,4536,10003,204
    SRC = ID_SCHACHTART
    VAL_ATTR = function
    -> AttributeFilter_4
AttributeFilter_4
    ATTR_VALUES = <EMPTY>,<MISSING>,<NULL>,<UNFILTERED>,1
    ATTR_NAME = ID_AERATION
    <EMPTY> -> AttributeValueMapper_3
    <UNFILTERED> -> AttributeValueMapper_3
    <NULL> -> AttributeValueMapper_3
    1 -> AttributeCreator_2
Note: aeration
AttributeCreator_2
    ATTR_LIST = function,4533
    -> AttributeValueMapper_3
Note: statut
AttributeValueMapper_3
    DIRECTION = Forward (Source To Destination)
    LUT = 1,6528,6,6530,3,6526,4,3633,7,3027,5,6523
    SRC = ID_STATUS
    VAL_ATTR = status
    -> StringLengthFormatter
Note: remark TBC
StringLengthFormatter
    StringLength = 80
    Input_Attr = @Value(remark)
    RESULT_Attr = remark
    -> FeatureMerger_3 [input 1]
FeatureMerger_3
    MERGE_TYPE = Attributes Only
    JOIN_KEYS = @Value(old_obj_id) @Value(FID_SCHACHT) AUTO
    SUPPLIERS_FIRST = No
    PROCESS_DUPS = No
    ATTR_ACCUM_MODE = Merge Supplier
    ATTR_CONFLICT_RES = Use Requestor
    MERGED -> AttributeRemover
AttributeRemover
    REMOVE_ATTRS = ABDECKPLATTE,ACCURACY_LEVEL,ANSCHLUESSE,ANZAHL_AUSLAEUFE,ANZAHL_EINLAEUFE,AREA,AREA_NOMINAL,AVG_DEV_XY,AVG_DEV_Z,AZIMUTH,BAUGRUBENBREITE,BEZEICHNUNG1,BEZEICHNUNG2,BOESCHUNGSWINKEL,CALC_CODE,CALC_NUMBER,CHAMBRE_ANCIENID,CHAMBRE_CLASSE,CHAMBRE_CONTROLE,CHAMBRE_NUMEROECA,CHAMBRE_PARCELLE,CHAMBRE_PLAN,CHAMBRE_TYPE,CLIPPING,COMMUNE,CREATION_CODE_XY_1,CREATION_CODE_XY_2,CREATION_CODE_XY_3,CREATION_CODE_XY_4,CREATION_CODE_XY_5,CREATION_CODE_Z,DA,DATE_CREATED,DATE_DELETED,DATE_MODIFIED,DELETED,DIM_X,DIM_Y,DTEXT,ESEQ,ETYPE,F1,F2,F3,FID,FID_COLLECTEUR,FID_EINRICHTUNGS_TYP,FID_KS,FID_LAGEBEZEICHNUNG,FIELD_CODE,FLAECHE,FRAME,GEO_CONSTRAINT,GID,ID,ID_AERATION,ID_BAUGRUBENFORM,ID_BEGR_BESCHICHTUNG,ID_BESCHICHTUNG_AUSSEN,ID_BESCHICHTUNG_INNEN,ID_BRISECHARGE,ID_COMMUNE,ID_COUPEVENT,ID_EIGENTUMSVERHAELTNIS,ID_EINSTIEGHILFE,ID_FINANZIERUNGSKENNZIFFER,ID_FUNKTION,ID_GERINNE_BAUSTOFF,ID_GERINNE_FORM,ID_GRUENDUNG,ID_HOEHENGENAUIGKEIT,ID_KONUS_BAUSTOFF,ID_LAGE,ID_LAGEGENAUIGKEIT,ID_LIMITEURDEBIT,ID_MATERIAL,ID_NUTZUNGS_ART,ID_OBEN_BAUSTOFF,ID_PROFIL,ID_PROFIL_CHAMBRE,ID_SCHACHT_FORM,ID_SCHACHTART,ID_STATUS,ID_STEIGEISENGAENGE,ID_STRASSE,ID_UNTEN_BAUSTOFF,ID_UNTEN_FORM,ID_VERKEHRSFLAECHE,ID_ZUGAENGLICHKEIT,INVISIBLE,KOMPLEX_LABEL,LABEL_FROM,LABEL_TEXT,LABEL_TO,LETZTER_UEBERSTAU,LINEATTRIBUTE_ID,LONGUEUR,M_DIRECTION,M_DISTANCE,MUTATION_ID_CREATED,MUTATION_ID_DELETED,MUTATION_ID_MODIFIED,MUTATION_STATUS_CREATED,MUTATION_STATUS_DELETED,NAME,ORIENTATION,ORIGIN,PERIMETER,POINT_NUMBER,QUALITY,SBW,SCHACHTHALS,SEQ,SEQ_ETYPE,SEQ_PARAM1,SEQ_PARAM1_2,SEQ_PARAM1_3,SEQ_PARAM1_4,SEQ_PARAM1_5,SEQ_PARAM2,SEQ_PARAM2_2,SEQ_PARAM2_3,SEQ_PARAM2_4,SEQ_PARAM2_5,SEQ_PARAM3,SEQ_PARAM3_2,SEQ_PARAM3_3,SEQ_PARAM3_4,SEQ_PARAM3_5,SKALIERFAKTOR,SONDERBAUWERK,SOURCE,SPATIAL_INDEX_25,SPATIAL_INDEX_50,SPATIAL_INDEX_100,SPATIAL_INDEX_200,SPATIAL_INDEX_400,TB_POINT_NUMBER,TD_DA,TD_GROUP,TD_LAYER,TD_NUMBER,TD_POINT_NUMBER,UEBERGANGSPLATTE,UEBERSTAUHAEUFIGKEIT,UNTEN_BREITE,UNTEN_DN,USER_CREATED,USER_DELETED,USER_MODIFIED,WANDDICKE,X1,X2,X3,X4,X5,Y1,Y2,Y3,Y4,Y5,Z_DIFF,Z_TERRAIN,Z1,Z2,Z3,Z4,Z5
    -> qgep.vw_wizard_cover_manhole_sige (writer POSTGRES_2)
    -> Inspector
qgep.vw_wizard_cover_manhole_sige (writer POSTGRES_2)
    attributes: identifier varchar(80),PRIKEY, remark varchar(255), depth char(200), dimension1 char(200), dimension2 char(200), location_name char(200), bottom_level char(200), situation_geometry char(200), fk_owner char(200), material char(200), function char(200), year_of_construction char(200), year_of_replacement char(200), status char(200), node_geometry char(200), old_obj_id char(200)
Inspector
Inspector_2
AttributeRenamer_5
Note: aeration
AttributeValueMapper_5
    DIRECTION = Forward (Source To Destination)
    LUT = 1,229,0,230
    DEFAULT_VALUE = 5348
    SRC = ID_AERATION
    VAL_ATTR = venting

FME custom transformer oracle_geom_point

Parameters:
- Y1 = @Value(Y1)
- X1 = @Value(X1)
- GID = @Value(GID)

geom_table (input)
    -> StringFormatter
StringFormatter
    SRC_ATTRS = X1,Y1
    FORMAT = .10f
    -> StringConcatenator
StringConcatenator
    VAL_ATTR = WKT
    PARM_LINE = POINT(,&Y1, ,&X1, )
    -> GeometryReplacer
GeometryReplacer
    ATTR = WKT
    SRS_AXIS_ORDER_DISPLAY = Automatic
    KIND_LONG = OGC Well Known Text
    -> GeometryOGCValidator
GeometryOGCValidator
    VALIDATION_TYPE = Simple
    PASSED -> CoordinateSystemSetter
    FAILED -> failed_geom (output)
CoordinateSystemSetter
    COORDSYS = EPSG:21781
    -> GeometryExtractor
GeometryExtractor
    OGCVERSION = 1.1
    ATTR = geometry
    KIND_LONG = OGC Well Known Binary
    -> StringConcatenator_2
StringConcatenator_2
    ACTION = Create New Attribute
    VAL_ATTR = geometry
    PARM_LINE = SRID=21781;@Value(geometry)
    -> AttributeRemover
AttributeRemover
    REMOVE_ATTRS = WKT,X1,Y1
    -> FeatureMerger_2 [input 2]
failed_geom (output)
main_table (input)
    -> FeatureMerger_2 [input 1]
Note: geometrie
FeatureMerger_2
    MERGE_TYPE = Attributes Only
    REFERATTR = GID
    BUILD_INCOMPLETE = No
    REFEEATTR = GID
    PROCESS_DUPS = No
    COMPLETE -> FeatureMerger_2_Complete (output)
    INCOMPLETE -> unfound_geom (output)
FeatureMerger_2_Complete (output)
unfound_geom (output)

FME custom transformer StringLengthFormatter
Formats attributes to the specified length either truncating or padding the incoming attributes. 
For example, if you set the String Length parameter to 5:
- If an input attribute value consists of only 3 characters, this transformer will add two spaces to the end of the attribute value.
- If an input attribute value has a length of 7, this transformer will remove two characters from the end of it.
User has to connect this transformer in a workspace and choose a source attribute, a destination attribute and a desired string length.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- StringLength = 5   # String length
- Input_Attr =   # Source Attribute
- RESULT_Attr =   # Destination Attribute

INPUT (input)
    -> ParameterFetcher
Note: Retrieve parameters
ParameterFetcher
    ATTR_LIST = _slfLength {$(StringLength)} _slfSource {$(Input_Attr)}
    -> STRINGLENGTHCALCULATOR
Note: Determine the input string's length
STRINGLENGTHCALCULATOR: StringLengthCalculator
    SRC_ATTR = _slfSource
    LENGTH_ATTR = _slfSourceLength
    -> TESTER
Note: Created by Dmitri Bagh / November 11, 2005
Note: Check whether input / string is longer than / user's chosen length
TESTER: Tester
    TEST_DESCRIPTION = ""
    TEST_CLAUSE = TEST "@Value(_slfSourceLength)" > "@Value(_slfLength)"
    BOOL_OP = OR
    TEST_LIST = &_slfSourceLength,>,&_slfLength
    TEST_MODE = Automatic
    FAILED -> STRINGPADDER
    PASSED -> ExpressionEvaluator
Note: If it is shorter or equal, run it / through the StringPadder
STRINGPADDER: StringPadder
    SIDE = Right
    WIDTH = @Value(_slfLength)
    SRC = _slfSource
    RESULT = $(RESULT_Attr)
    -> ATTRIBUTEREMOVER
Note: Clean up
ATTRIBUTEREMOVER: AttributeRemover
    REMOVE_ATTRS = _slfLength,_slfSource,_slfSourceLength
    -> OUTPUT (output)
OUTPUT (output)

Bookmark: If it is longer, remove the extra characters
ExpressionEvaluator
    EXPRESSION = @Value(_slfLength)-1
    VAL_ATTR = _slfLength
    -> SUBSTRINGEXTRACTOR
SUBSTRINGEXTRACTOR: SubstringExtractor
    SRC_ATTR = _slfSource
    START = 0
    RESULT_ATTR = $(RESULT_Attr)
    END = @Value(_slfLength)
    -> ATTRIBUTEREMOVER
